;;; ============================================================
;;; 属性块-柜宽缩放.lsp   v8                 命令：GKW
;;; ------------------------------------------------------------
;;; 作用：按倍数缩放「槽位版柜属性块」的宽度。
;;;       末列（数量列）宽度保持原值不变，增量全部给左侧列；
;;;       同排右侧的块自动跟随平移，保持间距。
;;;       倍数 < 1 即缩窄，逻辑完全相同。
;;;
;;; 位移口径（D = 原宽 x (倍数 - 1)）：
;;;       局部 x = 0          -> 不动
;;;       0 < 局部 x < 竖线x   -> 走 D/2
;;;       局部 x >= 竖线x      -> 走 D
;;;
;;; 共享定义的处理（关键）：
;;;   一排柜往往共用同一个块定义（例如三台柜都叫「开关柜-低压」）。
;;;   直接改定义会让整排一起变宽，所以：
;;;     - 该定义的参照不止一个、且没被全选中  -> 先给目标参照「裂变」
;;;       出独立定义（复制 + 改参照块名），再只改这一份；
;;;     - 一次选中了该定义的全部参照          -> 视为整排加宽，不裂变。
;;;
;;; 另：判断「右侧的块」用的是缩放前的包围盒 —— 改定义后包围盒会
;;;     立刻变大，用新的会把邻居判成「不在右侧」，一个都不推。
;;;
;;; 占位块（一次方案图那种纯几何块，块里没有 ATTDEF）的处理：
;;;   - 被改宽的柜：它罩住的占位块水平**居中**到柜块新中心（竖直不动）。
;;;     占位块自身宽度不变，只是摆回柜子正中间。
;;;   - 被推走的柜：占位块跟着一起平移，不会留在原地跟柜子错开。
;;;   识别口径：不是属性块 + 包围盒中心落在柜块包围盒内 + 高度不小于柜高 10%
;;;             + **不是把柜块包住的外框**。
;;;   （判据只看纵向尺寸：柜子放大后「柜宽一半」会超过占位块的固定宽度，
;;;     用它当门槛会导致缩回时认不出占位块。）
;;;
;;; 图框 / 图纸边框：**永不参与任何位移**。
;;;   判据是几何事实 —— 谁的包围盒把柜块**整个包住**，谁就是外框。
;;;   绝不能靠块名认（图框块名五花八门：*U53 / A3 / 图框-1 …）。
;;;   为什么必须专门挡：图框的包围盒中心往往正好落在某一台柜的包围盒
;;;   里（实测 D1 宽 105 时，柜心 x 与图框中心 x 都是 132.8），会被上面
;;;   那条「占位块」判据误判 → 加宽时图框跟着被「居中」平移走。
;;;
;;; 识别方式（三重闸门，缺一不认）：
;;;   1) 块定义里必须含 ATTDEF（属性定义）—— 挡掉占位块这类纯几何块，
;;;      否则会把一幅图形当表格拉伸（这坑踩过）；
;;;   2) 「最长的一条内部垂直线」= 分栏竖线，没有就跳过；
;;;   3) 该竖线左右两侧都必须有属性对齐点，确认真是表格分栏线。
;;;   块宽 = 块内所有图元的最大 x（含柜框 LWPOLYLINE）。
;;;   表头块没有分栏竖线，会被明确跳过并提示。
;;;
;;; 编码：ANSI/GBK 无 BOM
;;; ============================================================
(vl-load-com)

;; ---------------------------------------------------------------
;; 位移量：局部 x -> 该走多少
;; ---------------------------------------------------------------
(defun gkw:shift (lx vx dd)
  (cond
    ((< (abs lx) 1e-6) 0.0)
    ((< lx vx) (/ dd 2.0))
    (t dd)
  )
)

;; ---------------------------------------------------------------
;; 给实体数据里所有组码 10 / 11 的 x 统一加 dd
;; ---------------------------------------------------------------
(defun gkw:addx (ed dd / out x p)
  (setq out nil)
  (foreach x ed
    (if (or (= 10 (car x)) (= 11 (car x)))
      (progn
        (setq p (cdr x))
        (setq out (cons (cons (car x) (cons (+ (car p) dd) (cdr p))) out))
      )
      (setq out (cons x out))
    )
  )
  (reverse out)
)

;; ---------------------------------------------------------------
;; 逐点判定：每个组码 10 / 11 按自己的 x 算位移（LINE / LWPOLYLINE）
;; ---------------------------------------------------------------
(defun gkw:eachpt (ed vx dd / out x p)
  (setq out nil)
  (foreach x ed
    (if (or (= 10 (car x)) (= 11 (car x)))
      (progn
        (setq p (cdr x))
        (setq out (cons (cons (car x)
                              (cons (+ (car p) (gkw:shift (car p) vx dd)) (cdr p)))
                        out))
      )
      (setq out (cons x out))
    )
  )
  (reverse out)
)

;; ---------------------------------------------------------------
;; 整体判定：按「对齐点」算一次位移，10 与 11 一起走（ATTDEF / TEXT）
;;   base = 参照插入点 x（块定义里传 0）
;; ---------------------------------------------------------------
(defun gkw:shiftpts (ed vx dd base / p d)
  (setq p (cdr (assoc 11 ed)))
  (if (null p) (setq p (cdr (assoc 10 ed))))
  (if (null p)
    ed
    (progn
      (setq d (gkw:shift (- (car p) base) vx dd))
      (gkw:addx ed d)
    )
  )
)

;; ---------------------------------------------------------------
;; 量块定义：返回 (块宽 分栏竖线x 属性对齐点x列表 最小x)
;;   第三个值是「这是不是属性块」的判据 —— 纯几何块（如占位块）
;;   没有 ATTDEF，必须挡在外面，否则会把一幅图形当表格拉伸。
;;   第四个值（最小 x）用来配合插入点算块的中心 —— 见 gkw:center。
;; ---------------------------------------------------------------
(defun gkw:geom (bn / b e ed ty w vs vx vl p1 p2 v axs pt p wn)
  (setq b (tblobjname "BLOCK" bn) w 0.0 wn 1e9 vs nil axs nil e (entnext b))
  (while (and e (/= "ENDBLK" (cdr (assoc 0 (setq ed (entget e))))))
    (setq ty (cdr (assoc 0 ed)))
    (cond
      ((= ty "LWPOLYLINE")
       (foreach pt (vl-remove-if-not '(lambda (q) (= 10 (car q))) ed)
         (if (> (car (cdr pt)) w) (setq w (car (cdr pt))))
         (if (< (car (cdr pt)) wn) (setq wn (car (cdr pt))))
       )
      )
      ((= ty "LINE")
       (setq p1 (cdr (assoc 10 ed)) p2 (cdr (assoc 11 ed)))
       (if (> (car p1) w) (setq w (car p1)))
       (if (> (car p2) w) (setq w (car p2)))
       (if (< (car p1) wn) (setq wn (car p1)))
       (if (< (car p2) wn) (setq wn (car p2)))
       (if (equal (car p1) (car p2) 1e-6)
         (setq vs (cons (list (car p1) (abs (- (cadr p1) (cadr p2)))) vs))
       )
      )
      ((= ty "ATTDEF")
       (setq p (cdr (assoc 11 ed)))
       (if (null p) (setq p (cdr (assoc 10 ed))))
       (if p (setq axs (cons (car p) axs)))
      )
    )
    (setq e (entnext e))
  )
  (if (> wn 1e8) (setq wn 0.0))
  (setq vx nil vl 0.0)
  (foreach v vs
    (if (and (> (car v) 1e-6) (< (car v) (- w 1e-6)) (> (cadr v) vl))
      (setq vx (car v) vl (cadr v))
    )
  )
  (list w vx axs wn)
)

;; ---------------------------------------------------------------
;; 改块定义：柜框 / 行线 / 竖线 / 属性 / 静态文字 一起重排
;; ---------------------------------------------------------------
(defun gkw:edit (bn vx dd / b e ed ty)
  (setq b (tblobjname "BLOCK" bn) e (entnext b))
  (while (and e (/= "ENDBLK" (cdr (assoc 0 (setq ed (entget e))))))
    (setq ty (cdr (assoc 0 ed)))
    (cond
      ((= ty "LWPOLYLINE")
       (entmod (gkw:eachpt ed vx dd))
      )
      ((= ty "LINE")
       (entmod (gkw:eachpt ed vx dd))
      )
      ((member ty '("ATTDEF" "TEXT" "MTEXT" "CIRCLE" "ARC" "POINT" "SOLID"))
       (entmod (gkw:shiftpts ed vx dd 0.0))
      )
    )
    (setq e (entnext e))
  )
)

;; ---------------------------------------------------------------
;; 取块参照上的属性值（按 TAG）
;; ---------------------------------------------------------------
(defun gkw:tag (e tag / sub ed out)
  (setq sub (entnext e) out nil)
  (while (and sub (= "ATTRIB" (cdr (assoc 0 (setq ed (entget sub))))))
    (if (= tag (cdr (assoc 2 ed))) (setq out (cdr (assoc 1 ed))))
    (setq sub (entnext sub))
  )
  out
)

;; ---------------------------------------------------------------
;; 从块定义里找某 TAG 的属性定义（ATTDEF）
;; ---------------------------------------------------------------
(defun gkw:attdef (bn tag / b e ed res)
  (setq b (tblobjname "BLOCK" bn) e (entnext b) res nil)
  (while (and e (/= "ENDBLK" (cdr (assoc 0 (setq ed (entget e))))))
    (if (and (null res) (= "ATTDEF" (cdr (assoc 0 ed))) (= tag (cdr (assoc 2 ed))))
      (setq res ed)
    )
    (setq e (entnext e))
  )
  res
)

;; ---------------------------------------------------------------
;; 按块定义把参照的属性位置对齐回去（替代不可靠的 -ATTSYNC）
;;   已知前提：参照无旋转、无缩放
;; ---------------------------------------------------------------
(defun gkw:relayout (e / ed bn ins sub ed2 ad p10 p11 out)
  (setq ed (entget e) bn (cdr (assoc 2 ed)) ins (cdr (assoc 10 ed)))
  (setq sub (entnext e) out 0)
  (while (and sub (= "ATTRIB" (cdr (assoc 0 (setq ed2 (entget sub))))))
    (setq ad (gkw:attdef bn (cdr (assoc 2 ed2))))
    (if ad
      (progn
        (setq p10 (cdr (assoc 10 ad)) p11 (cdr (assoc 11 ad)))
        (setq ed2 (subst (cons 10 (list (+ (car ins) (car p10))
                                        (+ (cadr ins) (cadr p10))
                                        (+ (caddr ins) (caddr p10))))
                         (assoc 10 ed2) ed2))
        (if (assoc 11 ed2)
          (setq ed2 (subst (cons 11 (list (+ (car ins) (car p11))
                                          (+ (cadr ins) (cadr p11))
                                          (+ (caddr ins) (caddr p11))))
                           (assoc 11 ed2) ed2))
        )
        (entmod ed2)
        (setq out (1+ out))
      )
    )
    (setq sub (entnext sub))
  )
  out
)

;; ---------------------------------------------------------------
;; 整体平移一个块参照（连同它的属性）
;; ---------------------------------------------------------------
(defun gkw:move (e dd / ed p sub)
  (setq ed (entget e) p (cdr (assoc 10 ed)))
  (entmod (subst (cons 10 (cons (+ (car p) dd) (cdr p))) (assoc 10 ed) ed))
  (setq sub (entnext e))
  (while (and sub (= "ATTRIB" (cdr (assoc 0 (setq ed (entget sub))))))
    (entmod (gkw:addx ed dd))
    (setq sub (entnext sub))
  )
)

;; ---------------------------------------------------------------
;; 包围盒
;;   实测有些块参照（图里那几个 BLK_* 方案图块）调 GetBoundingBox 会
;;   直接报 eInvalidInput（「范围无效」）—— 不加保护，整条命令当场崩。
;;   读不到时退回「插入点 + 定义几何范围 × 缩放」自己推一个：无旋转
;;   缩放下两者等价，拿来判左右、判谁包住谁够用。
;;   连块定义都找不到的（返回 nil）由调用方跳过。
;; ---------------------------------------------------------------
(defun gkw:bb (e / o mn mx r bn b ee de ip sc dx0 dy0 dx1 dy1 x y)
  ;; ★ 模态 DCL 回调里 ActiveX 未必可用（连 vla-object 都可能抛），
  ;;   整段包住；读不到就退回下面「插入点 + 定义几何」自己推。
  (setq r (vl-catch-all-apply
            (function (lambda ()
              (setq o (vlax-ename->vla-object e))
              (vla-GetBoundingBox o 'mn 'mx)
              (list (vlax-safearray->list mn) (vlax-safearray->list mx))))))
  (if (not (vl-catch-all-error-p r))
    r
    (progn
      (setq bn (cdr (assoc 2 (entget e))) ip (cdr (assoc 10 (entget e))))
      (setq b (tblobjname "BLOCK" bn) ee (if b (entnext b) nil))
      (setq dx0 1e9 dy0 1e9 dx1 -1e9 dy1 -1e9)
      (while (and ee (/= "ENDBLK" (cdr (assoc 0 (setq de (entget ee))))))
        (foreach pr de
          (if (and (member (car pr) '(10 11))
                   (listp (cdr pr)) (numberp (car (cdr pr))))
            (progn
              (setq x (car (cdr pr)) y (cadr (cdr pr)))
              (if (< x dx0) (setq dx0 x)) (if (> x dx1) (setq dx1 x))
              (if (< y dy0) (setq dy0 y)) (if (> y dy1) (setq dy1 y))
            )
          )
        )
        (setq ee (entnext ee))
      )
      (if (> dx0 dx1)
        nil
        (progn
          (setq sc (cdr (assoc 41 (entget e))) sc (if (and sc (> sc 0.0)) sc 1.0))
          (list (list (+ (car ip) (* dx0 sc)) (+ (cadr ip) (* dy0 sc)) 0.0)
                (list (+ (car ip) (* dx1 sc)) (+ (cadr ip) (* dy1 sc)) 0.0))
        )
      )
    )
  )
)

;; ---------------------------------------------------------------
;; 是不是「把柜块整个包住的外框」（图框 / 图纸边框）
;;   判据：它的包围盒左右上下都把柜块包在里面。
;;   图框永远满足；同排右边的柜块永远不满足（左边界不会伸到柜块左侧）；
;;   柜内占位块也不满足（比柜子窄）。
;;   这类块**一律不平移**，无论它是被推还是被居中。
;; ---------------------------------------------------------------
(defun gkw:frame (mn mx mn2 mx2)
  (and (<= (car mn2) (+ (car mn) 0.01))
       (>= (car mx2) (- (car mx) 0.01))
       (<= (cadr mn2) (+ (cadr mn) 0.01))
       (>= (cadr mx2) (- (cadr mx) 0.01)))
)

;; ---------------------------------------------------------------
;; 块定义里有没有 ATTDEF —— 也就是「是不是属性块」
;;   占位块这类纯几何块必须靠这一条挡在外面
;; ---------------------------------------------------------------
(defun gkw:attrp (bn / b e ed r)
  (setq b (tblobjname "BLOCK" bn) e (entnext b) r nil)
  (while (and e (null r) (/= "ENDBLK" (cdr (assoc 0 (setq ed (entget e))))))
    (if (= "ATTDEF" (cdr (assoc 0 ed))) (setq r T))
    (setq e (entnext e))
  )
  r
)

;; ---------------------------------------------------------------
;; 依据原始快照，找出「被该柜块罩住」的纯几何块参照（占位块 / 方案图）
;;   判据：① 不是属性块；
;;         ② **不是把柜块整个包住的外框**（图框千万别动）；
;;         ③ 包围盒中心落在柜块包围盒内（边界算里）；
;;         ④ 高度不小于柜高的 10% —— 挡掉图纸里的零碎小装饰块。
;;   ④ 为什么看高度不看宽度：柜子被放大之后「柜宽的一半」会超过
;;   占位块自身的固定宽度，用它当门槛，缩回时就认不出占位块了
;;   （实测踩过：×2 认得出、×0.5 认不出，占位块就留在原地）。
;;   纵向尺寸不受横向缩放影响，用它最稳。
;; ---------------------------------------------------------------
(defun gkw:holders (e snap / itm mn mx res o2 mn2 mx2)
  (setq itm (assoc e snap) res nil)
  (if itm
    (progn
      (setq mn (cadr itm) mx (caddr itm))
      (foreach o2 snap
        (if (not (eq (car o2) e))
          (progn
            (setq mn2 (cadr o2) mx2 (caddr o2))
            (if (and (not (gkw:attrp (cdr (assoc 2 (entget (car o2))))))
                     (not (gkw:frame mn mx mn2 mx2))
                     (>= (/ (+ (car mn2) (car mx2)) 2.0) (- (car mn) 1e-6))
                     (<= (/ (+ (car mn2) (car mx2)) 2.0) (+ (car mx) 1e-6))
                     (>= (/ (+ (cadr mn2) (cadr mx2)) 2.0) (- (cadr mn) 1e-6))
                     (<= (/ (+ (cadr mn2) (cadr mx2)) 2.0) (+ (cadr mx) 1e-6))
                     (>= (- (cadr mx2) (cadr mn2)) (* 0.1 (- (cadr mx) (cadr mn)))))
              (setq res (cons (car o2) res))
            )
          )
        )
      )
    )
  )
  res
)

;; ---------------------------------------------------------------
;; 全图所有「已被某个柜块罩住」的占位块
;;   推右侧的块时要跳过它们 —— 否则会被推两遍：一遍作为宿主的
;;   随从，一遍作为「自己也在右边」的独立块（实测就是这么双推的）。
;; ---------------------------------------------------------------
(defun gkw:allholders (snap / res itm)
  (setq res nil)
  (foreach itm snap
    (if (gkw:attrp (cdr (assoc 2 (entget (car itm)))))
      (foreach h (gkw:holders (car itm) snap)
        (if (not (member h res)) (setq res (cons h res)))
      )
    )
  )
  res
)

;; ---------------------------------------------------------------
;; 把柜块罩住的占位块水平居中到柜块的新中心（竖直方向不动）
;;   必须在 gkw:edit 之后调用。
;;   这里不读柜块的包围盒，直接用「插入点 + 定义几何」推 —— 无旋转
;;   缩放下 bbox 就等于 插入点 + 定义几何，而插入点是 entget 实时读的，
;;   不必赌包围盒缓存在什么时候刷新：
;;       新中心 = 插入点x + 定义最小x + (新宽度 / 2)
;;   这样柜块自己先前被推走、或这一轮已经加宽过，都算得对。
;;   返回居中了几个
;; ---------------------------------------------------------------
(defun gkw:center (e w dd mnx snap / ip cx1 cnt h bb2 cx)
  (setq ip (cdr (assoc 10 (entget e))))
  (setq cx1 (+ (car ip) mnx (/ (+ (- w mnx) dd) 2.0)))
  (setq cnt 0)
  (foreach h (gkw:holders e snap)
    (setq bb2 (gkw:bb h))
    (if bb2
      (progn
        (setq cx (/ (+ (car (car bb2)) (car (cadr bb2))) 2.0))
        (if (> (abs (- cx1 cx)) 1e-6)
          (progn (gkw:move h (- cx1 cx)) (setq cnt (1+ cnt)))
        )
      )
    )
  )
  cnt
)

;; ---------------------------------------------------------------
;; 平移一个柜块，连它罩住的占位块一起走
;;   不这么做：左边柜加宽把右边柜整体推走时，右边柜头顶的占位块
;;   会留在原地，跟柜子直接错开。
;; ---------------------------------------------------------------
(defun gkw:move2 (e dd snap / cnt)
  (gkw:move e dd)
  (setq cnt 1)
  (foreach h (gkw:holders e snap)
    (gkw:move h dd)
    (setq cnt (1+ cnt))
  )
  cnt
)

;; ---------------------------------------------------------------
;; 开工前把所有块参照的包围盒拍个快照（实体名 . (min max)）
;;   判「谁在谁右侧」必须用这份**原始布局**：
;;   改定义会让命中块的包围盒立刻变大，用当前值判会把邻居判成
;;   「不在右侧」；整排一起加宽时更会因为前一台已经推过而算漏。
;; ---------------------------------------------------------------
(defun gkw:snapshot ( / ss i n lst e bbx)
  (setq ss (ssget "X" '((0 . "INSERT"))) i 0 n (if ss (sslength ss) 0) lst nil)
  (while (< i n)
    (setq e (ssname ss i) bbx (gkw:bb e))
    ;; bbx 为 nil = 连块定义都找不到，只能跳过；
    ;; 「读不到包围盒」的已由 gkw:bb 兜底推算，照常入册。
    (if bbx (setq lst (cons (list e (car bbx) (cadr bbx)) lst)))
    (setq i (1+ i))
  )
  lst
)

;; ---------------------------------------------------------------
;; 把原始布局里位于该块右侧、且同排的块，按**当前位置**平移 dd
;;   snap 元素形如 (图元名 最小点 最大点)
;;   hs  = 全图的占位块清单，这些不单独推（它们跟着宿主走）
;;   被推的块连同它罩住的占位块一起走（gkw:move2）
;;   外框（图框）永不被推 —— 它把柜块整个包住，一旦被推整张图就散了
;;   返回平移了几个
;; ---------------------------------------------------------------
(defun gkw:push (e dd snap hs / itm mn mx o2 mn2 mx2 cnt)
  (setq itm (assoc e snap) cnt 0)
  (if itm
    (progn
      (setq mn (cadr itm) mx (caddr itm))
      (foreach o2 snap
        (if (and (not (eq (car o2) e)) (not (member (car o2) hs)))
          (progn
            (setq mn2 (cadr o2) mx2 (caddr o2))
            (if (and (not (gkw:frame mn mx mn2 mx2))
                     (>= (car mn2) (- (car mx) 0.01))
                     (> (- (min (cadr mx) (cadr mx2))
                           (max (cadr mn) (cadr mn2))) 0.01))
              (progn (gkw:move2 (car o2) dd snap) (setq cnt (1+ cnt)))
            )
          )
        )
      )
    )
  )
  cnt
)

;; ---------------------------------------------------------------
;; 该块定义在图上有几个参照
;; ---------------------------------------------------------------
(defun gkw:refs (bn / ss i n lst)
  (setq ss (ssget "X" (list '(0 . "INSERT") (cons 2 bn))) i 0 n (sslength ss) lst nil)
  (while (< i n) (setq lst (cons (ssname ss i) lst)) (setq i (1+ i)))
  lst
)

;; ---------------------------------------------------------------
;; 由参照的「柜号」推一个不重名的块名
;; ---------------------------------------------------------------
(defun gkw:newname (bn e / tag cand i)
  (setq tag (gkw:tag e "柜号"))
  (if (or (null tag) (= tag "")) (setq tag "1"))
  (setq cand (strcat bn "-" tag) i 1)
  (while (tblobjname "BLOCK" cand)
    (setq cand (strcat bn "-" tag "(" (itoa i) ")") i (1+ i))
  )
  cand
)

;; ---------------------------------------------------------------
;; 复制块定义（entmake 重建；去掉 owner / handle 等会冲突的组码）
;; ---------------------------------------------------------------
(defun gkw:clone (old new / b e ed lst)
  (setq b (tblobjname "BLOCK" old) e (entnext b) lst nil)
  (while (and e (/= "ENDBLK" (cdr (assoc 0 (setq ed (entget e))))))
    (setq lst (cons ed lst))
    (setq e (entnext e))
  )
  (setq lst (reverse lst))
  (entmake (list '(0 . "BLOCK") '(100 . "AcDbEntity") '(8 . "0")
                 '(100 . "AcDbBlockBegin") (cons 2 new) (cons 3 new)
                 '(70 . 0) '(10 0.0 0.0 0.0) '(4 . "")))
  (foreach ed lst
    (entmake (vl-remove-if '(lambda (x) (member (car x) '(5 330 102 360))) ed))
  )
  (entmake '((0 . "ENDBLK") (100 . "AcDbEntity") (8 . "0") (100 . "AcDbBlockEnd")))
  (tblobjname "BLOCK" new)
)

;; ---------------------------------------------------------------
;; 把参照指向另一个块定义
;; ---------------------------------------------------------------
(defun gkw:setblock (e nb / ed)
  (setq ed (entget e))
  (entmod (subst (cons 2 nb) (assoc 2 ed) ed))
)

;; ---------------------------------------------------------------
;; 全局参数：宽度调整步长 / 最小允许宽度（两者相同，均为 35）
;; ---------------------------------------------------------------
(setq *gkw-step* 35.0)

;; ---------------------------------------------------------------
;; 主逻辑（可脱离交互直接调用）
;;   ss = 选择集，dd0 = 宽度增减量（正数增加，负数减少，通常传 ±35）
;; ---------------------------------------------------------------
(defun gkw:run (ss dd0 / i n e lst item bn g w vx dd nw defs res m c
                refs allsel pb newbn g0 selcnt snap axs hs mnx rl
                hsn eh hh mm h2)
  ;; 原始布局快照（必须在任何改动之前拍）
  (setq snap (gkw:snapshot))
  ;; 全图占位块清单（推块时跳过它们）
  (setq hs (gkw:allholders snap))
  ;; 按插入点 x 从左到右排
  (setq lst nil i 0 n (sslength ss))
  (while (< i n)
    (setq e (ssname ss i))
    (setq lst (cons (cons (car (car (gkw:bb e))) e) lst))
    (setq i (1+ i))
  )
  (setq lst (vl-sort lst '(lambda (a b) (< (car a) (car b)))))
  ;; 统计每个块名被选中了几个
  (setq selcnt nil)
  (foreach item lst
    (setq bn (cdr (assoc 2 (entget (cdr item)))))
    (setq selcnt (if (assoc bn selcnt)
                   (subst (cons bn (1+ (cdr (assoc bn selcnt)))) (assoc bn selcnt) selcnt)
                   (cons (cons bn 1) selcnt)))
  )
  (setq defs nil res "")
  (foreach item lst
    (setq e (cdr item) bn (cdr (assoc 2 (entget e))))
    (setq g (assoc bn defs))
    (if (null g)
      (progn
        (setq g0 (gkw:geom bn) w (car g0) vx (cadr g0) axs (caddr g0) mnx (cadddr g0))
        (setq pb nil dd 0.0 newbn nil)
        (cond
          ((null axs)
           (setq res (strcat res "\n  [" bn "] 不是属性块（块内没有属性定义），跳过"))
          )
          ((null vx)
           (setq res (strcat res "\n  [" bn "] 没有分栏竖线，跳过"))
          )
          ((or (null (vl-remove-if-not '(lambda (x) (< x vx)) axs))
               (null (vl-remove-if-not '(lambda (x) (> x vx)) axs)))
           (setq res (strcat res "\n  [" bn "] 分栏竖线两侧没有配对的属性列，跳过"))
          )
          ((and (< dd0 0.0) (< (+ w dd0) (- *gkw-step* 1e-6)))
           (setq res (strcat res "\n  [" bn "] 已到最小宽度 " (rtos *gkw-step* 2 0) "，不能再减少，跳过"))
          )
          ((< (+ vx dd0) 2.0)
           (setq res (strcat res "\n  [" bn "] 宽度太小，左列会被压没，跳过"))
          )
          (t
           (setq dd dd0 nw (+ w dd))
           (setq refs (gkw:refs bn))
           (setq allsel (= (length refs) (cdr (assoc bn selcnt))))
           (setq pb bn)
           (if (not allsel)
             (progn
               (setq newbn (gkw:newname bn e))
               (gkw:clone bn newbn)
               (gkw:setblock e newbn)
               (setq pb newbn)
             )
           )
           (gkw:edit pb vx dd)
           (setq res (strcat res "\n  [" bn "] 宽 " (rtos w 2 2)
                             " -> " (rtos nw 2 2)
                             "，末列 " (rtos (- w vx) 2 2) " 保持不变"
                             (if newbn (strcat "，已裂变出独立定义 " newbn) "")))
          )
        )
        (setq g (list bn pb vx dd newbn mnx w))
        (setq defs (cons g defs))
      )
    )
    ;; 生效：属性按定义对齐 + 占位块居中 + 右侧的块跟随平移
    (if (nth 1 g)
      (progn
        (gkw:relayout e)
        (setq c (gkw:center e (nth 6 g) (nth 3 g) (nth 5 g) snap))
        (if (> c 0)
          (setq res (strcat res "\n      " (itoa c) " 个占位块已居中"))
        )
        (setq m (gkw:push e (nth 3 g) snap hs))
        (if (> m 0)
          (setq res (strcat res "\n      右侧 " (itoa m) " 个块已跟随平移"))
        )
      )
    )
  )
  ;; ---- 缩放完成后：按新宽度重排整排行高 ----
  ;;   放在所有块都改完之后 —— gh:apply 会重造整排参照，句柄全变，
  ;;   必须在 GKW 自己的位移/居中都做完之后再动它。
  (if lst
    (progn
      (setq rl nil hsn nil)
      (foreach item lst
        (setq eh (cdr item))
        (setq rl (cons eh rl))
        (setq hsn (cons (cdr (assoc 5 (entget eh))) hsn))
      )
      (setq rl (reverse rl) hsn (reverse hsn))
      (setq res (strcat res (gkw:rerow rl)))
      ;; 整排参照被重造过 -> 旧实体名失效。按 旧句柄->新句柄 映射留一份
      ;;   新实体表给 c:GKW（重开对话框时重建选择集；此时 DCL 已关，
      ;;   改图是安全的）。
      (setq *gkw:newents* nil)
      (if *gkw:map*
        (progn
          (foreach hh hsn
            (setq mm (assoc hh *gkw:map*))
            (setq h2 (handent (if mm (cadr mm) hh)))
            (if h2 (setq *gkw:newents* (cons h2 *gkw:newents*)))
          )
          (setq *gkw:newents* (reverse *gkw:newents*))
        )
      )
    )
  )
  (princ (strcat "\nGKW 宽度调整 " (if (>= dd0 0.0) "+" "") (rtos dd0 2 2)))
  (princ res)
  res
  (princ "\n")
  ;; 返回提示文本：命令行交互看不出差别，但被 run_lisp 一类的
  ;; 脚本调用时，拿得到字符串才能当场核对，否则拿到 nil、
  ;; 外面 strcat 就报 "参数类型错误: stringp"。
  res
)

;; ---------------------------------------------------------------
;; 生成临时 DCL 文件：一个带「增加 / 减少」按钮的对话框
;;   用完即删，不需要跟 lsp 一起分发单独的 .dcl 文件。
;; ---------------------------------------------------------------
(defun gkw:dclfile ( / path f stepstr)
  (setq stepstr (rtos *gkw-step* 2 0))
  (setq path (vl-filename-mktemp "gkw.dcl"))
  (setq f (open path "w"))
  (write-line "gkw_dlg : dialog {" f)
  (write-line (strcat "  label = \"柜宽调整（步长 " stepstr "）\";") f)
  (write-line "  : text { key = \"msg\"; width = 46; fixed_width = true; }" f)
  (write-line "  : text { key = \"cur_w\"; }" f)
  (write-line "  : row {" f)
  (write-line (strcat "    : button { key = \"inc\"; label = \"增加 +" stepstr "\"; width = 14; fixed_width = true; }") f)
  (write-line (strcat "    : button { key = \"dec\"; label = \"减少 -" stepstr "\"; width = 14; fixed_width = true; }") f)
  (write-line "  }" f)
  (write-line "  spacer_1;" f)
  (write-line "  : button { key = \"close\"; label = \"关闭\"; is_cancel = true; width = 14; }" f)
  (write-line "}" f)
  (close f)
  path
)

;; ---------------------------------------------------------------
;; 取选择集里所有块定义（去重）当前的最小宽度；找不到有效属性块时返回 nil
;; ---------------------------------------------------------------
(defun gkw:mincur (ss / i n bn seen minw w0)
  (setq i 0 n (sslength ss) seen nil minw nil)
  (while (< i n)
    (setq bn (cdr (assoc 2 (entget (ssname ss i)))))
    (if (not (member bn seen))
      (progn
        (setq seen (cons bn seen))
        (setq w0 (car (gkw:geom bn)))
        (if (or (null minw) (< w0 minw)) (setq minw w0))
      )
    )
    (setq i (1+ i))
  )
  minw
)

;; ---------------------------------------------------------------
;; 刷新对话框：显示当前（选中块里最小的）宽度，并按 35 的下限
;;   决定「减少」按钮是否可用
;; ---------------------------------------------------------------
(defun gkw:refresh-dlg (ss / minw)
  (setq minw (gkw:mincur ss))
  (if minw
    (progn
      (set_tile "cur_w" (strcat "当前宽度：" (rtos minw 2 2)))
      (if (< minw (+ *gkw-step* 1e-6))
        (mode_tile "dec" 3)
        (mode_tile "dec" 4)
      )
    )
    (set_tile "cur_w" "当前宽度：--（选中里没有可识别的属性块）")
  )
)

;; ================================================================
;; 七、缩放后行高重排（2026-09-24 增）
;; ================================================================
;; 为什么要有这一步
;;   柜宽一改，规格栏的可容宽度就跟着变 —— 原来要 3 行才放下的规格，
;;   加宽后 2 行就够；反过来缩窄会从 1 行变 2 行。所以每次缩放之后都要
;;   按【缩放后的实际宽度】重做一次换行判定，再按结果增减行高。
;;   行高必须【整排统一】：槽位块定义是整排共用的，改一处就是整排一起
;;   变；判定也一样，要拿整排最长的规格去算，不能只看被点的那一台。
;;
;; 宽度口径（2026-09-24 实测，与 PLT 完全对得上）
;;   规格栏 = 分栏竖线左边那一整块，左边界 = 块定义最小 x（实测 0）
;;   可容宽度 em = (分栏竖线 x - 块最小 x) / 字高
;;   实测：竖线 27、左 0、字高 3.0 -> 9.0 em
;;         与 属性块-一键出图 的 *plt:slot-col* 一模一样
;;         （那条注释写的「27 列宽 / 3.0 字高」说的就是这个数）
;;   缩放后竖线走全量 dd、左边界不动：
;;         实测加宽 35 -> 竖线 27 变 62，容量 9.0 -> 20.7 em
;;   ★ 表头块没有分栏竖线（gkw 本来就不缩放它），量不出容量 -> 不参与
;;
;; 依赖
;;   换行判定（plt:wrap / czt:dump-spec）和增减行高（gh:apply）都在
;;   「属性块-一键出图-集成版.lsp」里，这里按需 load 一次。
;;   gh:apply 只在该排【确实需要加/减行】时才调 —— 它会重造整排参照
;;   （句柄全变、定义名加后缀），没必要就别惊动它。
;; ================================================================

(setq *gkw:rowsmax* 9)   ; 单槽最多几行（与 XBT 的 *xbt:rowsmax* 同口径）

;; 依赖候选路径：先是同目录（相对名靠 CAD 搜索路径），再是两个绝对位置
(setq gkw:deps
  (list "属性块-一键出图-集成版.lsp"
        "D:/kk三部曲/93.lisp管理工具/测试/代码/lisp/属性块-一键出图-集成版.lsp"
        "D:/kk三部曲/148.CAD插件研究/lisp/属性块-一键出图-集成版.lsp"
        "D:/kk三部曲/148.CAD插件研究/lisp/属性块-槽位增减.lsp"))

;; 内核在不在；不在就按候选路径 load 一次。返回 T / nil
(defun gkw:ensure ( / ps p ok)
  (if (and plt:wrap czt:dump-spec gh:apply)
    T
    (progn
      (setq ok nil)
      (foreach p gkw:deps
        (if (null ok)
          (progn
            (setq ps (findfile p))
            (if ps
              (progn
                (setq p (vl-catch-all-apply 'load (list ps)))
                (if (and (not (vl-catch-all-error-p p)) plt:wrap gh:apply)
                  (setq ok T)
                )
              )
            )
          )
        )
      )
      ok
    )
  )
)

;; 块定义里 ATTDEF 的字高（取头一个；本套块一律 3.0）
(defun gkw:texth (bn / b sub ed h)
  (setq b (tblobjname "BLOCK" bn) h nil)
  (if b
    (progn
      (setq sub (entnext b))
      (while (and sub (/= "ENDBLK" (cdr (assoc 0 (setq ed (entget sub))))))
        (if (and (null h) (= "ATTDEF" (cdr (assoc 0 ed))))
          (setq h (cdr (assoc 40 ed)))
        )
        (setq sub (entnext sub))
      )
    )
  )
  h
)

;; 块定义里「规格」栏的可容宽度（em）= (竖线 x - 块最小 x) / 字高
;;   没有竖线（表头块）或不属性块 -> nil
(defun gkw:cap (bn / g0 vx wn h)
  (setq g0 (gkw:geom bn) vx (cadr g0) wn (cadddr g0))
  (setq h (gkw:texth bn))
  (if (and vx h (> h 0.0) (> (- vx wn) 0.0))
    (/ (- vx wn) h)
  )
)

;; 与给定参照【同一排】的所有属性块参照
;;   判据 = 插入点 y 与 refs 里任意一个差 < 1.0
;;   一次选了好几排（y 不同）就都纳进来 —— 行高取全部参照
;;   的最大行数，宁可宽松不可溢出。
;;   占位块 / 图框不是属性块，被 gkw:attrp 挡在外面。
(defun gkw:sameref (refs / ys out ss i n e ed bn yy hit y0)
  (setq ys nil)
  (foreach y0 refs
    (setq ys (cons (cadr (cdr (assoc 10 (entget y0)))) ys))
  )
  (setq out nil)
  (setq ss (ssget "_X" '((0 . "INSERT") (410 . "Model"))))
  (if ss
    (progn
      (setq i 0 n (sslength ss))
      (while (< i n)
        (setq e (ssname ss i) ed (entget e) bn (cdr (assoc 2 ed))
              yy (cadr (cdr (assoc 10 ed))) hit nil)
        (if (numberp yy)
          (foreach y0 ys
            (if (< (abs (- yy y0)) 1.0) (setq hit T))
          )
        )
        (if (and hit (gkw:attrp bn))
          (setq out (cons e out))
        )
        (setq i (1+ i))
      )
    )
  )
  (reverse out)
)

;; 整排行数计划：逐槽取全排最大（空规格恒 1 行）
;;   ★ 每台按【自己的】规格栏宽度算行数，再取最大 —— 不能拿整排
;;     统一的一个宽度（尤其不能取最窄那台）算所有台：那样只加宽
;;     其中一台时，加宽的那台仍被按旧窄宽度重算，等于把加宽效果抹掉
;;     （2026-09-24 实测：只加宽变压器柜 -> 行数不变，就是这个原因）。
;;   逐台算再取 max 一样安全：每台算出的行数必然 ≤ plan[k]，文字
;;     只会少占行、由 plt:midrow 居中，绝不会溢出柜框。
;;   宽度按块名缓存，避免逐槽重扫块定义。
(defun gkw:rowplan (refs need / pl k mx e rw c bn cm)
  (setq pl "" cm nil)
  (foreach e refs
    (setq bn (cdr (assoc 2 (entget e))))
    (if (null (assoc bn cm)) (setq cm (cons (cons bn (gkw:cap bn)) cm)))
  )
  (foreach k (plt:seq 1 need)
    (setq mx 1)
    (foreach e refs
      (setq bn (cdr (assoc 2 (entget e))))
      (setq c (cdr (assoc bn cm)))
      (if (null c) (setq c *plt:slot-col*))
      (setq rw (length (plt:wrap (czt:dump-spec (plt:atts e) k) c)))
      (if (> rw mx) (setq mx rw))
    )
    (if (> mx *gkw:rowsmax*) (setq mx *gkw:rowsmax*))
    (setq pl (strcat pl (if (= pl "") "" ",") (itoa mx)))
  )
  pl
)

;; 按新宽度把每槽规格重新拆行写回。返回写了几槽。
;;   mp    = gh:apply 返回的 ((旧句柄 新句柄 新定义名) ...)
;;   snap2 = ((旧句柄 (槽1文本 槽2文本 ...)) ...)
;;   ★ 拆行宽度逐台取【自己的】新 cap，临时顶掉全局 *plt:slot-col*
;;     （plt:putspec / plt:wrap 读的就是它），写完必须还原 ——
;;     否则后续 XBT / PLT 会拿错宽度。
;;     不能拿整排统一的一个宽度（尤其最窄那台）来拆：那样加宽过的那台
;;     又被按窄宽度重拆，行数不会变少，前面的 plan 也就白算了。
;;   表头块没有规格属性 -> dump-spec 全空 -> 自然跳过。
(defun gkw:refill (mp snap2 need / nw oc s m nref atts k v rw c bn)
  (setq nw 0 oc *plt:slot-col*)
  (foreach m mp
    (setq s (assoc (car m) snap2))
    (if s
      (progn
        (setq nref (handent (cadr m)) atts (if nref (plt:atts nref) nil))
        (if atts
          (progn
            ;; gh:apply 之后参照已换到缩放后的定义名，gkw:cap 量的就是该台新宽度
            (setq bn (cdr (assoc 2 (entget nref))))
            (setq c (gkw:cap bn))
            (setq *plt:slot-col* (if c c oc))
            (foreach k (plt:seq 1 need)
              (setq v (nth (1- k) (cadr s)))
              (if (and v (/= v ""))
                (progn
                  (setq rw (plt:putspec atts k v T))
                  (setq nw (1+ nw))
                  (if (and (> (cadr rw) 0) (> (caddr rw) 0) (< (caddr rw) (cadr rw)))
                    (plt:midrow nref k (cadr rw) (caddr rw))
                  )
                )
              )
            )
          )
        )
      )
    )
  )
  (setq *plt:slot-col* oc)
  nw
)

;; 行高不用动，但某台柜的规格文字还按【旧宽度】拆着行 —— 只加宽其中一台
;;   就是这种局面：整排 plan 被最窄那台顶住，gh:deltas 判「与现状一致」，
;;   主流程整个收手，加宽过的那台文字照旧占着 3 行。
;;   -> 就地按【各自的新宽度】重拆写回：不走 gh:apply，句柄与行高都不动，
;;      定义名也不会再加后缀。只对「格子里现存的行 ≠ 按自身宽度应有的行」
;;      的台动手，重复跑幂等。返回真正重拆的台数。
(defun gkw:respec (refs need / mp snap2 n e bn c k v rows m j ok cur want
                            atts s5 txts nn a)
  (setq mp nil snap2 nil n 0)
  (foreach e refs
    (setq bn (cdr (assoc 2 (entget e))) c (gkw:cap bn))
    (if c
      (progn
        (setq atts (plt:atts e) ok T txts nil)
        (foreach k (plt:seq 1 need)
          (setq v (czt:dump-spec atts k))
          (setq txts (cons v txts))
          (if (/= v "")
            (progn
              (setq rows (plt:wrap v c))
              ;; 格数口径必须与 plt:putspec 一致：取「规格N」里最大的 N；
              ;;   一个都没有(0) = 该槽是旧的单行形态，标签就叫「规格」。
              ;;   ★ 不能用 gh:cur 代替 —— 它对单行形态也答 1，于是把
              ;;     「元件0N规格」当成「元件0N规格1」去取值，落到空串，
              ;;     误判成「需要重拆」（2026-09-24 实测踩到）。
              (setq m 0)
              (foreach a atts
                (setq nn (plt:specno (car a) k))
                (if (> nn m) (setq m nn))
              )
              (if (> m 0)
                (progn
                  (setq j 1)
                  (while (<= j m)
                    (setq cur (plt:val atts (plt:tagk k (strcat "规格" (itoa j)))))
                    (setq want (if (nth (1- j) rows) (nth (1- j) rows) ""))
                    (if (/= (if cur cur "") want) (setq ok nil))
                    (setq j (1+ j))
                  )
                )
                (progn
                  (setq cur (plt:val atts (plt:tagk k "规格")))
                  (setq want (if (car rows) (car rows) ""))
                  (if (/= (if cur cur "") want) (setq ok nil))
                )
              )
            )
          )
        )
        (if (null ok)
          (progn
            (setq s5 (cdr (assoc 5 (entget e))))
            (setq mp (cons (list s5 s5 bn) mp))
            (setq snap2 (cons (list s5 (reverse txts)) snap2))
            (setq n (1+ n))
          )
        )
      )
    )
  )
  (if (> n 0) (gkw:refill mp snap2 need))
  n
)

;; 主流程：按缩放后的宽度重排整排行高。返回报告串（追加到 GKW 报告里）
(defun gkw:rerow (refs / rs cap c e need plan hs bn2 any rp snap2 sp2 nw2 nsp)
  (setq *gkw:map* nil)
  (if (null (gkw:ensure))
    "\n  行高重排跳过：没找到「属性块-一键出图-集成版.lsp」（plt:wrap / gh:apply 在里面）"
    (progn
      (setq rs (gkw:sameref refs))
      ;; ① 最窄那台的规格栏宽度 —— 仅作提示和「量不出宽度就跳过」的门槛。
      ;;    ★ 行数判定不按它算（那样只加宽一台会被抹平），改由
      ;;      gkw:rowplan 逐台按各自宽度算，见那里的注释。
      (setq cap nil)
      (foreach e rs
        (setq c (gkw:cap (cdr (assoc 2 (entget e)))))
        (if (and c (or (null cap) (< c cap))) (setq cap c))
      )
      (if (null cap)
        "\n  行高重排跳过：本排量不出规格栏宽度（块内没有分栏竖线或属性）"
        (progn
          ;; ② 槽数 = 全排最大槽号
          (setq need 0)
          (foreach e rs
            (setq c (plt:slotmax (plt:atts e)))
            (if (> c need) (setq need c))
          )
          (if (< need 1)
            "\n  行高重排跳过：本排没数出槽位"
            (progn
              ;; ③ 计划：整排逐槽取最大
              (setq plan (gkw:rowplan rs need))
              ;; ④ 先看这一排【是否真的要动】：全排所有带规格属性的块
              ;;    都算一遍 deltas，全空就直接收手 —— gh:apply 会重造
              ;;    整排参照（句柄全变、定义名加后缀），不必白跑一趟。
              (setq any nil)
              (foreach e rs
                (setq bn2 (cdr (assoc 2 (entget e))))
                (if (and (null any) (gh:hasspec bn2) (gkc:geo bn2))
                  (if (gh:deltas bn2 plan) (setq any T))
                )
              )
              (if (null any)
                (progn
                  (setq nsp (gkw:respec rs need))
                  (if (> nsp 0)
                    (strcat "\n  行高重排：计划 " plan " 与现状一致（行高不动）；"
                            "其中 " (itoa nsp) " 台的规格文字已按缩放后宽度重拆")
                    (strcat "\n  行高重排：计划 " plan "，与现状一致，没动"
                            "（最窄柜规格栏 " (rtos cap 2 2) " em）")
                  )
                )
                (progn
                  ;; ⑤ gh:apply 之前先把每槽的【完整规格文本】抓下来 ——
                  ;;    重排会重造参照、多出来的行被删掉，
                  ;;    值只能自己接住再写回。
                  (setq snap2 nil)
                  (foreach e rs
                    (setq sp2 nil)
                    (foreach k (plt:seq 1 need)
                      (setq sp2 (cons (czt:dump-spec (plt:atts e) k) sp2))
                    )
                    (setq snap2 (cons (list (cdr (assoc 5 (entget e))) (reverse sp2)) snap2))
                  )
                  (setq hs "")
                  (foreach e rs
                    (setq hs (strcat hs (if (= hs "") "" ",") (cdr (assoc 5 (entget e)))))
                  )
                  (setq rp (vl-catch-all-apply 'gh:apply (list hs plan)))
                  (if (vl-catch-all-error-p rp)
                    (strcat "\n  行高重排失败：" (vl-catch-all-error-message rp)
                            "（图已改宽，可单独敲 GGH 补行高）")
                    (progn
                      ;; 句柄映射 ((旧句柄 新句柄 新定义名) ...) ——
                      ;;   给 c:GKW 重建选择集用（整排参照已被重造）
                      (setq *gkw:map* (cadr rp))
                      (setq nw2 (vl-catch-all-apply 'gkw:refill
                                                    (list (cadr rp) snap2 need)))
                      (if (vl-catch-all-error-p nw2) (setq nw2 0))
                      (strcat "\n  行高重排：" (itoa (length rs)) " 个参照，计划 " plan
                              "（最窄柜规格栏 " (rtos cap 2 2) " em），回写 " (itoa nw2) " 槽规格"
                              "\n      注：gh:apply 重造了整排参照 —— 句柄已变、"
                              "定义名带柜号后缀，这是它的既定行为")
                    )
                  )
                )
              )
            )
          )
        )
      )
    )
  )
)


;; ---------------------------------------------------------------
;; 命令外壳：选块后弹出「增加 / 减少」对话框，每点一次按 35 步长调整
;; ---------------------------------------------------------------
;; ---------------------------------------------------------------
;; 去掉前导空白
;; ---------------------------------------------------------------
(defun gkw:trim2 (s / i n)
  (setq i 1 n (strlen s))
  (while (and (<= i n) (= " " (substr s i 1))) (setq i (1+ i)))
  (substr s i)
)

;; ---------------------------------------------------------------
;; 取报告里第一条非空行（DCL 的单行 text 只放得下一行），过长截断
;; ---------------------------------------------------------------
(defun gkw:brief (s / i n cur ch done out)
  (setq i 1 n (strlen s) cur "" done nil out "")
  (while (and (<= i n) (null done))
    (setq ch (substr s i 1))
    (if (= ch "\n")
      (progn
        (setq cur (gkw:trim2 cur))
        (if (/= cur "") (setq out cur done T))
        (setq cur "")
      )
      (setq cur (strcat cur ch))
    )
    (setq i (1+ i))
  )
  (if (and (null done) (/= (gkw:trim2 cur) "")) (setq out (gkw:trim2 cur)))
  (if (> (strlen out) 58) (setq out (strcat (substr out 1 58) "...")))
  out
)

;; ---------------------------------------------------------------
;; 命令外壳：选块后弹出「增加 / 减少」对话框
;;   点「增加 / 减少」：只记下方向并关闭对话框，界面立刻消失；
;;   对话框关掉之后再执行改图，结果打印在命令行。
;;   （改图放在对话框外面，DCL 已关，不受「回调里不能用 command」限制。）
;;   点「关闭」/ 按 ESC / 点右上角 X：什么都不做，直接退出。
;;   要继续调整就再敲一次 GKW。
;; ---------------------------------------------------------------
(defun c:GKW ( / ss dclpath dclid r)
  (princ "\n选择要调整宽度的属性柜块（可多选）: ")
  (setq ss (ssget '((0 . "INSERT"))))
  (if (null ss)
    (princ "\n没选到块。")
    (progn
      (setq dclpath (gkw:dclfile))
      (setq dclid (load_dialog dclpath))
      (setq *gkw:dir* nil)
      (if (or (null dclid) (< dclid 0))
        (princ "\n对话框加载失败。")
        (progn
          (if (new_dialog "gkw_dlg" dclid)
            (progn
              (gkw:refresh-dlg ss)
              (action_tile "inc" "(setq *gkw:dir* 1) (done_dialog 1)")
              (action_tile "dec" "(setq *gkw:dir* -1) (done_dialog 1)")
              (action_tile "close" "(setq *gkw:dir* nil) (done_dialog 0)")
              (start_dialog)
            )
          )
          (unload_dialog dclid)
        )
      )
      (if (and dclpath (findfile dclpath)) (vl-file-delete dclpath))
      ;; 对话框已经关了，这里再执行改图
      (if *gkw:dir*
        (progn
          (setq r (vl-catch-all-apply 'gkw:run (list ss (* *gkw:dir* *gkw-step*))))
          (if (vl-catch-all-error-p r)
            (princ (strcat "\nGKW 出错：" (vl-catch-all-error-message r)))
          )
          (setq *gkw:dir* nil)
        )
      )
    )
  )
  (princ)
)

(princ "\n[属性块-柜宽缩放] 已加载，命令：GKW")
(princ)
