;;; ================================================================
;;; 属性块-一键出图-集成版.lsp          命令：CZT
;;; ----------------------------------------------------------------
;;; 单文件集成版说明
;;;   本文件把以下 6 个原始文件的源码按依赖顺序原样合并成【一个】
;;;   .lsp 文件，功能与原来完全一致，只是不再需要在同一目录下再放
;;;   五个依赖文件——appload 这一个文件即可：
;;;     1 属性块-槽位增减.lsp   （GKC 内核：增减槽位，其余模块都靠它重建块）
;;;     2 属性块-增加行高.lsp   （GH：单槽加行高，靠 GKC 内核重建）
;;;     3 属性块-箱变.lsp       （XBT：箱变两段铺图，靠 PGT/GKC/GH/PLT）
;;;     4 属性块-铺图.lsp       （PGT：KYN28 单段铺图骨架）
;;;     5 属性块-批量填数.lsp   （PLT：清单解析 / 灌数 / 图签，其余模块共用其解析口径）
;;;     6 属性块-一键出图.lsp   （CZT：集成调度层 + 剪贴板粘贴交互入口，见文件末尾）
;;;   以下每个模块的原始文件头注释都完整保留在对应分隔线之后，
;;;   便于按原文档追查某个模块内部的实现细节。
;;;
;;;   ★ 交互入口（CZT 命令）与配套网页工具对接：
;;;     配套的「箱变生成器」「KYN28 生成器」两个网页工具点一下「写回」
;;;     按钮，会按 CZT/PLT/XBT 认得的格式（图签/表头 用 | 分隔、柜头行
;;;     @ 开头、元件行 名称|型号|规格|数量、末尾带一段 # 开头的槽位
;;;     顺序块——注意：该块不是纯核对用的，它是本程序排【表头槽位】
;;;     的定义来源，plt:sdefs 会按它给元件定槽，见「二、解清单」）
;;;     自动把清单文本复制到 Windows 剪贴板；回到 CZT 对话框点
;;;     「粘贴剪贴板清单 → 一键出图」，程序直接从剪贴板取文本，一次跑完
;;;     判型 → 铺壳 → 灌数 → 读回。也可以点「改从 TXT 文件读取…」走
;;;     原来的选文件流程。两个入口都能勾选「只预演」「先清空重铺」或
;;;     强制指定 KYN28 / 箱变两段。
;;;
;;;   模板 dwg（图框模版.dwg / 柜块模版.dwg / 表头块模版.dwg / 占位块.dwg）
;;;   仍需按各模块注释所述路径单独放好——这些是图纸资源，不是代码，
;;;   合并 .lsp 文件不能把它们也带进来。
;;;
;;;   本文件编码 ANSI/GBK，无 BOM。
;;; ================================================================

(vl-load-com)
(if (not (boundp 'SEP)) (setq SEP (chr 10)))



;;; ================================================================
;;; 模块 一、内核模块：属性块-槽位增减.lsp（GKC，命令 GKC）
;;; ================================================================

;;; ============================================================
;;; 属性块-槽位增减.lsp                                      命令：GKC
;;; ------------------------------------------------------------
;;; 作用
;;;   给「一排」属性块（柜块 + 表头块）在行区【底部】一次增减 N
;;;   个标准槽位行（N 默认 1）。整排（含表头）同步增减 —— 不必
;;;   一块一块地点。
;;;
;;; 两个入口
;;;   ① 手动：命令 GKC —— 点本排任意一个属性块（或多选整排），
;;;      再选增 / 减、给个数。带几何认段，适合人在图上临时改。
;;;   ② 被导入工具调用：MCP 侧（attkit import）比对差异时本来就
;;;      知道「哪一排、要加几个槽」（导入模板里就有块名 / 柜号 /
;;;      句柄），所以这条按句柄直达；但会先用 gkc:rowfill 把
;;;      「紧密相接的一整行」按几何补齐 —— 只给半排句柄时不再静默
;;;      只扩一半（高低压紧贴成一行时最容易踩，2026-09-18 实测）：
;;;          (gkc:plan   "句柄,句柄,..." N)   只读清单，图不动
;;;          (gkc:expand "句柄,句柄,..." N)   执行
;;;      N 负数 = 减槽。
;;;
;;; 「本排」怎么圈（只对手动入口有意义）
;;;   先按 y 区间圈出同一水平带的所有属性块，再按「x 相接」从
;;;   选中的那块向两侧扩展 —— 只要紧贴在一起就算本排，不再按
;;;   槽数是否相同来切分。槽数不同的块并进同一排后，增/减时
;;;   各块按自身现有槽数分别 +N / -N，互不影响。
;;;
;;; 纵向几何口径（全部实测得来，不写死数字）
;;;   ① 柜块顶部（顶部数据容器）、列标题行、以及【已有全部槽位】
;;;      一律原地不动；
;;;   ② 增减那 N 行占的空间从【行区底部】腾出 / 收回 ——
;;;        增：底部区（备注行 / 容量功率行 / 空白行）整体下移 N 个
;;;            行距，N 个新槽插在行区最底，块底跟着向下长 N 个行距；
;;;        减：底部区整体上移 N 个行距，行区最底 N 槽被删掉，
;;;            块底跟着向上收 N 个行距。
;;;      说白了就是「备注行、功率行上下移动，柜顶恒定」。
;;;   ③ 所有图元共用一条判定规则（LINE / LWPOLYLINE / ATTDEF /
;;;      TEXT / MTEXT 一律照此办理）：
;;;          点的 y <= 行区底线 B  ->  增则 -N*pitch，减则 +N*pitch
;;;      于是柜框底边、分栏竖线底端、底部区那几条横线、备注与
;;;      容量功率属性自动跟着走；顶边与上部属性天然不动。
;;;   ④ 行区底线 B 那条横线：
;;;        增 N 行时【原地保留】（它变成最上那个新槽的顶线），
;;;        另在 B-pitch, B-2*pitch, ... B-N*pitch 处补画 N 条
;;;        （各新槽的底线）；
;;;        减 N 行时把最底 N 条（B, B+pitch, ... B+(N-1)*pitch）删掉。
;;;   ⑤ 行区分栏竖线（穿过槽位行的 LINE 竖线，如「规格 | 数量」之间
;;;      那根）：下端一律吸附到行区底线上 ——
;;;        增 N 行时下端下移 N 个行距（不跟就会缺：新槽那一段没竖线），
;;;        减 N 行时下端上移 N 个行距（不跟就会拖到已删掉的行区里去）。
;;;      上端（行区顶）不动：加槽只往行区底部加，行区顶不挪。
;;;
;;; 一次到位
;;;   增 / 减 N 槽在【一趟重建】里做完，不循环调 N 次 —— 循环会让
;;;   参照重造 N 轮、句柄变 N 轮，表头块 of= 还得每轮追着改名。
;;;   K=1 时与「一次一槽」的老写法逐字等价。
;;;
;;; 槽位与槽号
;;;   槽位属性 tag 形如「元件NN规格」「元件NN数量」（表头块是
;;;   「元件NN名称」「元件NN型号」）。新槽号 = 现有最大 +1，两位
;;;   数补零。第 01 槽在一期图上占 3 个子行（18 高，规格1/2/3 +
;;;   数量），它【永远不参与】增减，也永远不当模板；模板固定取
;;;   【行区最底那一槽】（标准行）。
;;;
;;; 减的两道闸门（整排级）
;;;   ① 本排【任意】一个属性块、最底 N 槽的【任意】一个属性只要有
;;;      非空值 -> 整次拒绝，一个块都不动；
;;;   ② 减完剩下的槽数低于 *gkc:min*（默认 1）时拒绝。
;;;
;;; 槽数不必一致
;;;   本排各属性块的最大槽号可以不同，增/减时各块按自身现有
;;;   槽数分别处理，互不影响，不再要求先对齐。
;;;
;;; 共享定义
;;;   块定义一律「克隆成新名 + 把本排参照改指过去」的方式重建，
;;;   原定义原封不动 —— 别的排就算共用同一个定义也一个字不变。
;;;   新定义名 = 原名 + "-" + 该参照的柜号（表头块用「表头」）。
;;;   原定义的自描述串（Comments）一并带走，表头块 of= 里的柜块名同步
;;;   改成新名；slots 数值 ±N、slotrows 补 / 去 N 项。少了这一步，
;;;   MCP 侧 acad_att_bom 认不到表头块、acad_att_panel 会判「没建过」重画。
;;;
;;; 报告
;;;   命令提示与执行结果都写详细：逐块列出槽数、新旧定义名、
;;;   同步了几个参照、底部区移了多少、拒绝的具体原因与所在块。
;;;
;;; 编码：ANSI/GBK 无 BOM
;;; ============================================================
(vl-load-com)
(setq SEP (chr 10))

;; ---------------- 常量 ----------------
(setq *gkc:pfx* "元件")   ; 槽位属性前缀
(setq *gkc:min* 1)        ; 至少保留几个槽（低于它拒绝再减）

;; ================================================================
;; 一、基础小工具
;; ================================================================

;; 去首尾空白
(defun gkc:trim (s / r)
  (if s
    (progn
      (setq r s)
      (while (and (> (strlen r) 0) (<= (ascii (substr r 1 1)) 32))
        (setq r (substr r 2)))
      (while (and (> (strlen r) 0) (<= (ascii (substr r (strlen r) 1)) 32))
        (setq r (substr r 1 (1- (strlen r)))))
      r)
    "")
)

;; 两位数补零：1 -> "01"
(defun gkc:pad2 (n)
  (if (< n 10) (strcat "0" (itoa n)) (itoa n))
)

;; 拼槽位 tag：元件 + NN + 后缀
(defun gkc:mktag (n sfx)
  (strcat *gkc:pfx* (gkc:pad2 n) sfx)
)

;; 从属性 tag 解析槽号：元件NNxxx -> NN；不是槽位属性返回 nil
;;   注意 AutoLISP 的 strlen / substr 按【字节】算，一个汉字 2 字节：
;;   「元件」= 4 字节，槽号固定 2 字节数字 —— 只取第 5、6 字节这个
;;   纯 ASCII 片段做 substr 永远安全（DBCS 陷阱就在这儿）。
(defun gkc:slotno (tg / s c1 c2)
  (if (and tg (>= (strlen tg) 6) (= (substr tg 1 4) *gkc:pfx*))
    (progn
      (setq s (substr tg 5 2))
      (setq c1 (ascii (substr s 1 1)) c2 (ascii (substr s 2 1)))
      (if (and (>= c1 48) (<= c1 57) (>= c2 48) (<= c2 57))
        (atoi s)
        nil))
    nil)
)

;; 取槽号之后的字段名：元件01规格1 -> 规格1 / 元件12数量 -> 数量
(defun gkc:suffix (tg)
  (substr tg 7)
)

;; 字符串列表拼成一段
(defun gkc:join (lst sep / r)
  (setq r "")
  (foreach s lst (setq r (if (= r "") s (strcat r sep s))))
  r
)

;; 输出报告（*gkc:quiet* 为真时一声不响 —— MCP 内部调用走这条）
(defun gkc:say (s)
  (if (not *gkc:quiet*)
    (progn
      (if s (princ s))
      (princ)
    )
  )
)

;; 块定义里所有图元的实体数据（按定义顺序）
(defun gkc:ents (bn / b e ed res)
  (setq b (tblobjname "BLOCK" bn) e (if b (entnext b) nil) res nil)
  (while (and e (/= "ENDBLK" (cdr (assoc 0 (setq ed (entget e))))))
    (setq res (cons ed res))
    (setq e (entnext e))
  )
  (reverse res)
)

;; 块定义里所有 ATTDEF 的实体数据
(defun gkc:attdefs (bn / res ed)
  (setq res nil)
  (foreach ed (gkc:ents bn)
    (if (= "ATTDEF" (cdr (assoc 0 ed))) (setq res (cons ed res)))
  )
  (reverse res)
)

;; 块定义里有没有 ATTDEF —— 也就是「是不是属性块」
(defun gkc:attrp (bn / b e ed r)
  (setq b (tblobjname "BLOCK" bn) e (if b (entnext b) nil) r nil)
  (while (and e (null r) (/= "ENDBLK" (cdr (assoc 0 (setq ed (entget e))))))
    (if (= "ATTDEF" (cdr (assoc 0 ed))) (setq r T))
    (setq e (entnext e))
  )
  r
)

;; ================================================================
;; 二、槽位几何（全部实测）
;; ================================================================

;; 槽位分组 -> ((槽号 最小y ATTDEF列表) ...)，按槽号升序
(defun gkc:slots (bn / res ed n y item)
  (setq res nil)
  (foreach ed (gkc:attdefs bn)
    (setq n (gkc:slotno (cdr (assoc 2 ed))))
    (if n
      (progn
        (setq y (caddr (assoc 10 ed)))
        (setq item (assoc n res))
        (if item
          (setq res (subst (list n (min (cadr item) y) (append (caddr item) (list ed)))
                           item res))
          (setq res (cons (list n y (list ed)) res))
        )
      )
    )
  )
  (vl-sort res '(lambda (a b) (< (car a) (car b))))
)

;; 行距：所有槽位属性 y 的相邻差里、出现次数最多的那个
;;   （实测柜块 = 6；第 01 槽内部子行也是 6，不会被带偏）
(defun gkc:pitch (bn / ys u d prev dd v cnt item best mx)
  (setq ys nil)
  (foreach ed (gkc:attdefs bn)
    (if (gkc:slotno (cdr (assoc 2 ed)))
      (setq ys (cons (caddr (assoc 10 ed)) ys))))
  (setq ys (vl-sort ys '<))
  (setq u nil)
  (foreach v ys
    (if (null (vl-remove-if '(lambda (x) (equal x v 0.01)) u))
      (setq u (cons v u))))
  (setq ys (vl-sort u '<))
  (setq d nil prev nil)
  (foreach v ys
    (if prev
      (progn
        (setq dd (- v prev))
        (if (> dd 0.01) (setq d (cons (atof (rtos dd 2 2)) d)))
      )
    )
    (setq prev v)
  )
  (setq cnt nil)
  (foreach v d
    (setq item (assoc v cnt))
    (if item
      (setq cnt (subst (cons v (1+ (cdr item))) item cnt))
      (setq cnt (cons (cons v 1) cnt))
    )
  )
  (setq best nil mx 0)
  (foreach v cnt
    (if (> (cdr v) mx) (progn (setq mx (cdr v)) (setq best (car v)))))
  best
)

;; 找 y 附近的那条横线（两端等高的 LINE），返回它的实体数据
(defun gkc:hline-ed (bn y / b e ed res best d)
  (setq b (tblobjname "BLOCK" bn) e (if b (entnext b) nil) res nil best 1e9)
  (while (and e (/= "ENDBLK" (cdr (assoc 0 (setq ed (entget e))))))
    (if (and (= "LINE" (cdr (assoc 0 ed)))
             (equal (caddr (assoc 10 ed)) (caddr (assoc 11 ed)) 1e-6))
      (progn
        (setq d (abs (- (caddr (assoc 10 ed)) y)))
        (if (< d best) (setq best d res ed))
      )
    )
    (setq e (entnext e))
  )
  (if (< best 1.0) res nil)
)

;; 一次算齐纵向几何 -> (行区底线B 行距P 最大槽号 槽表 最底槽 底线图元)
(defun gkc:geo (bn / sls low p y h off ln)
  (setq sls (gkc:slots bn))
  (if (null sls)
    nil
    (progn
      (setq p (gkc:pitch bn) p (if p p 6.0))
      (setq low (car (vl-sort sls '(lambda (a b) (< (cadr a) (cadr b))))))
      (setq y (cadr low))
      (setq h (cdr (assoc 40 (car (caddr low)))) h (if h h 3.0))
      (setq off (/ (- p h) 2.0))
      (setq B (- y off))
      (setq ln (gkc:hline-ed bn B))
      (if ln (setq B (caddr (assoc 10 ln))))
      (list B p (apply 'max (mapcar 'car sls)) sls low ln)
    )
  )
)

;; 某个槽的全部属性 tag
(defun gkc:slot-tags (bn n / res ed s)
  (setq res nil)
  (foreach ed (gkc:attdefs bn)
    (setq s (gkc:slotno (cdr (assoc 2 ed))))
    (if (and s (= s n)) (setq res (cons (cdr (assoc 2 ed)) res))))
  (reverse res)
)

;; 一段槽（lo..hi，闭区间）的全部属性 tag —— 减 K 槽时一次拿全，不够 K 个就少拿
(defun gkc:slot-tags-r (bn lo hi / res ed s)
  (setq res nil)
  (foreach ed (gkc:attdefs bn)
    (setq s (gkc:slotno (cdr (assoc 2 ed))))
    (if (and s (>= s lo) (<= s hi)) (setq res (cons (cdr (assoc 2 ed)) res))))
  (reverse res)
)

;; ================================================================
;; 三、包围盒 / 同排判定
;; ================================================================

;; 包围盒（读不到就按「插入点 + 定义几何」自己推）
(defun gkc:bb (e / o mn mx r bn b ee de ip sc dx0 dy0 dx1 dy1 x y)
  (setq o (vlax-ename->vla-object e))
  (setq r (vl-catch-all-apply 'vla-GetBoundingBox (list o 'mn 'mx)))
  (if (not (vl-catch-all-error-p r))
    (list (vlax-safearray->list mn) (vlax-safearray->list mx))
    (progn
      (setq bn (cdr (assoc 2 (entget e))) ip (cdr (assoc 10 (entget e))))
      (setq b (tblobjname "BLOCK" bn) ee (if b (entnext b) nil))
      (setq dx0 1e9 dy0 1e9 dx1 -1e9 dy1 -1e9)
      (while (and ee (/= "ENDBLK" (cdr (assoc 0 (setq de (entget ee))))))
        (foreach pr de
          (if (and (member (car pr) '(10 11))
                   (listp (cdr pr)) (numberp (car (cdr pr))))
            (progn
              (setq x (car (cdr pr)) y (cadr (cdr pr)))
              (if (< x dx0) (setq dx0 x)) (if (> x dx1) (setq dx1 x))
              (if (< y dy0) (setq dy0 y)) (if (> y dy1) (setq dy1 y))
            )
          )
        )
        (setq ee (entnext ee))
      )
      (if (> dx0 dx1)
        nil
        (progn
          (setq sc (cdr (assoc 41 (entget e))) sc (if (and sc (> sc 0.0)) sc 1.0))
          (list (list (+ (car ip) (* dx0 sc)) (+ (cadr ip) (* dy0 sc)) 0.0)
                (list (+ (car ip) (* dx1 sc)) (+ (cadr ip) (* dy1 sc)) 0.0))
        )
      )
    )
  )
)

;; 是不是「把柜块整个包住的外框」（图框）—— 这类块绝不参与判定
(defun gkc:frame (mn mx mn2 mx2)
  (and (<= (car mn2) (+ (car mn) 0.01))
       (>= (car mx2) (- (car mx) 0.01))
       (<= (cadr mn2) (+ (cadr mn) 0.01))
       (>= (cadr mx2) (- (cadr mx) 0.01)))
)

;; 开工前把所有块参照的包围盒拍个快照（实体名 . (最小点 最大点)）
(defun gkc:snapshot ( / ss i n lst e bbx)
  (setq ss (ssget "X" '((0 . "INSERT"))) i 0 lst nil
        n (if ss (sslength ss) 0))
  (while (< i n)
    (setq e (ssname ss i) bbx (gkc:bb e))
    (if bbx (setq lst (cons (list e (car bbx) (cadr bbx)) lst)))
    (setq i (1+ i))
  )
  lst
)

;; 本排：y 区间与 e 重叠的【属性块】参照（含 e 自己），不含图框
;; 定义的最大槽号（不是属性块 / 没有槽位 -> nil）
(defun gkc:maxslot (bn / g0)
  (setq g0 (gkc:geo bn))
  (if g0 (caddr g0) nil)
)

;; 相邻两块能不能连成同一段：只看 x 是否相接，不再要求槽数一致
;;   —— 紧贴在一起就算同一排，槽数不同也并成一排、统一增减
;;   （各按自身槽数分别处理）。n0 参数保留仅为兼容调用方，不再使用。
(defun gkc:adjoin (aa bb n0)
  (and (<= (car (cadr bb)) (+ (car (caddr aa)) 0.5))
       (>= (car (caddr bb)) (- (car (cadr aa)) 0.5)))
)

;; 本排：先按 y 重叠圈出「同一水平带」的属性块，再按「x 相接」
;;   从选中块向两侧扩展，切出这一段 —— 紧贴在一起就算同一排，
;;   不再按槽数是否相同来切分。槽数不同的块并进同一排后，增/减
;;   时各自按自身现有槽数分别处理，互不影响。
;;   实体一律按【句柄】认 —— 本机实测不同途径取到的实体名用 eq
;;   比会失手（段会切空），句柄是字符串，稳。
(defun gkc:row (e snap / eh itm mn mx band o2 mn2 mx2 n0 sorted idx i res)
  (setq eh (cdr (assoc 5 (entget e))) itm nil)
  (foreach o2 snap
    (if (and (null itm) (= (cdr (assoc 5 (entget (car o2)))) eh)) (setq itm o2))
  )
  (if (null itm)
    nil
    (progn
      (setq mn (cadr itm) mx (caddr itm) band (list itm))
      ;; 自己也算带内一员，但要【先跳过自己】再判「谁包住谁」——
      ;; 自己的包围盒当然包住自己，不跳过会被 frame 判据剔掉（踩过，
      ;; 表现就是段里没有自己、idx=-1、整段切空）。
      (foreach o2 snap
        (setq mn2 (cadr o2) mx2 (caddr o2))
        (if (and (/= (cdr (assoc 5 (entget (car o2)))) eh)
                 (gkc:attrp (cdr (assoc 2 (entget (car o2)))))
                 (not (gkc:frame mn mx mn2 mx2))
                 (> (- (min (cadr mx) (cadr mx2)) (max (cadr mn) (cadr mn2))) 0.01))
          (setq band (cons o2 band))
        )
      )
      (setq sorted (vl-sort band '(lambda (a b) (< (car (cadr a)) (car (cadr b))))))
      (setq n0 (gkc:maxslot (cdr (assoc 2 (entget e)))))
      (setq idx -1 i 0)
      (foreach o2 sorted
        (if (= (cdr (assoc 5 (entget (car o2)))) eh) (setq idx i))
        (setq i (1+ i))
      )
      (if (or (null n0) (< idx 0))
        nil
        (progn
          (setq res (list (nth idx sorted)))
          (setq i (1+ idx))
          (while (and (< i (length sorted))
                      (gkc:adjoin (nth (1- i) sorted) (nth i sorted) n0))
            (setq res (append res (list (nth i sorted))))
            (setq i (1+ i))
          )
          (setq i (1- idx))
          (while (and (>= i 0)
                      (gkc:adjoin (nth i sorted) (nth (1+ i) sorted) n0))
            (setq res (cons (nth i sorted) res))
            (setq i (1- i))
          )
          (mapcar 'car res)
        )
      )
    )
  )
)



;; 按几何把「紧密相接的一整行」补齐 —— MCP 口给句柄时也必须过这道。
;;   给一批参照 -> (整行参照列表 本次新补进来的参照列表)
;;   手动口单点选择走的就是 gkc:row；MCP 口以前不走 → 只给半排句柄就
;;   只扩半排；而 plan 的「漏参照」自检只比【同名块定义】，于是紧贴成
;;   一行的高低两段（块名不同）被漏掉时一声不响（2026-09-18 实测）。
;;   只读：只用 entget / 包围盒，图一个字节都不动。
(defun gkc:rowfill (refs / snap out seen add eh r x)
  (setq snap (gkc:snapshot) out nil seen nil add nil)
  (foreach e refs
    (setq eh (cdr (assoc 5 (entget e))))
    (if (not (member eh seen))
      (progn (setq seen (cons eh seen)) (setq out (cons e out))))
  )
  (foreach e refs
    (foreach x (gkc:row e snap)
      (setq eh (cdr (assoc 5 (entget x))))
      (if (not (member eh seen))
        (progn (setq seen (cons eh seen)) (setq add (cons x add)) (setq out (cons x out))))
    )
  )
  (list (reverse out) (reverse add))
)

;; 按块定义把本排参照分组 -> ((块名 参照1 参照2 ...) ...)
(defun gkc:groups (row / bydef bn rs)
  (setq bydef nil)
  (foreach rb row
    (setq bn (cdr (assoc 2 (entget rb))))
    (setq rs (assoc bn bydef))
    (if rs
      (setq bydef (subst (cons bn (append (cdr rs) (list rb))) rs bydef))
      (setq bydef (cons (list bn rb) bydef))
    )
  )
  bydef
)

;; ================================================================
;; 四、参照上的属性读写
;; ================================================================

;; 读参照的某个属性值
(defun gkc:tag (e tag / sub ed out)
  (setq sub (entnext e) out nil)
  (while (and sub (= "ATTRIB" (cdr (assoc 0 (setq ed (entget sub))))))
    (if (= tag (cdr (assoc 2 ed))) (setq out (cdr (assoc 1 ed))))
    (setq sub (entnext sub))
  )
  out
)

;; 用 -INSERT 重造参照：属性交给 CAD 自己实例化，再把旧值按 tag 迁回去
;;   为什么不是「给旧参照补属性」—— 本机 COM 没有 BlockReference.AddAttribute
;;   （实测「未知名称: AddAttribute」），entmake 单发 ATTRIB 也被拒；
;;   只有命令通道 _. -INSERT 会正常实例化属性。代价：参照句柄会变。
;;   drop = 不迁值的 tag 列表（减模式：已删掉的那一槽）
(defun gkc:newref (e newbn drop / pe lay rot scx scy p3 sub ed kv kv2 tag nv ed2 ne nc cl at nz nh)
  (setq pe (entget e))
  (setq nz (cdr (assoc 210 pe)))
  (if (and nz (not (equal nz '(0.0 0.0 1.0) 1e-6)))
    nil
    (progn
      (setq lay (cdr (assoc 8 pe)))
      (setq rot (cdr (assoc 50 pe)) rot (if rot rot 0.0))
      (setq scx (cdr (assoc 41 pe)) scx (if scx scx 1.0))
      (setq scy (cdr (assoc 42 pe)) scy (if scy scy 1.0))
      (setq p3 (cdr (assoc 10 pe)))
      (if (null (caddr p3)) (setq p3 (list (car p3) (cadr p3) 0.0)))
      ;; 旧参照的 tag -> 值
      (setq kv nil sub (entnext e))
      (while (and sub (= "ATTRIB" (cdr (assoc 0 (setq ed (entget sub))))))
        (setq kv (cons (cons (cdr (assoc 2 ed)) (cdr (assoc 1 ed))) kv))
        (setq sub (entnext sub))
      )
      (setq cl (getvar "CLAYER") at (getvar "ATTREQ"))
      (setvar "CLAYER" lay)
      (setvar "ATTREQ" 0)
      (command "_.-INSERT" newbn p3 scx scy rot)
      (setvar "ATTREQ" at)
      (setvar "CLAYER" cl)
      (setq ne (entlast) nc 0)
      (if (and ne (= "INSERT" (cdr (assoc 0 (entget ne))))
               (equal (cdr (assoc 2 (entget ne))) newbn))
        (progn
          (setq sub (entnext ne))
          (while (and sub (= "ATTRIB" (cdr (assoc 0 (setq ed (entget sub))))))
            (setq nc (1+ nc)) (setq sub (entnext sub))
          )
          ;; 防御：定义里有 ATTDEF、插出来却 0 属性 —— 块头少「含非常量属性」位。
          ;; 视为失败：删掉刚插的、保留旧参照，宁可不动也不丢数据。
          (if (and (gkc:attdefs newbn) (= nc 0))
            (progn (entdel ne) nil)
            (progn
              (setq sub (entnext ne))
              (while (and sub (= "ATTRIB" (cdr (assoc 0 (setq ed (entget sub))))))
                (setq tag (cdr (assoc 2 ed)) kv2 (assoc tag kv))
                (if (and kv2 (not (member tag drop)))
                  (progn
                    (setq nv (cdr kv2) ed2 nil)
                    (foreach q ed (setq ed2 (cons (if (= (car q) 1) (cons 1 nv) q) ed2)))
                    (entmod (reverse ed2))
                  )
                )
                (setq sub (entnext sub))
              )
              ;; 句柄必须在 entdel 之前取 —— 删了就问不出来了。
              ;; 返回【新句柄】而不是实体名：MCP 侧要拿它改写后续写入的目标。
              (setq nh (cdr (assoc 5 (entget ne))))
              (entdel e)
              nh
            )
          )
        )
        nil
      )
    )
  )
)

;; 由参照的柜号推一个不重名的块名（表头块用「表头」）
(defun gkc:newname (bn e / tg cand i)
  (setq tg (gkc:trim (gkc:tag e "柜号")))
  (if (= tg "") (setq tg (if (wcmatch bn "*表头*") "表头" "排")))
  (setq cand (strcat bn "-" tg) i 1)
  (while (tblobjname "BLOCK" cand)
    (setq cand (strcat bn "-" tg "(" (itoa i) ")") i (1+ i))
  )
  cand
)

;; ================================================================
;; 四之二、块定义元数据（Comments）维护
;; ================================================================
;; 块定义 Comments 里存着 MCP 侧的自描述串：
;;   柜块    "ACAD_BOM_CABINET|size=..|slots=15|prefix=元件|slotrows=1,2,.."
;;   表头块  "ACAD_BOM_HEADER|of=<柜块名>|size=..|slots=15|.."
;; acad_att_bom 靠 of= 认表头块、acad_att_panel 靠 slots / slotrows 判
;; 「这套参数是不是已经建过」。克隆块定义时必须把它带走 ——
;;   丢了 = 表头认不到（表头参照会被当柜计出幽灵行）、
;;          att_panel 误判「没建过」→ 重画，本次加减槽白干。
;; （2026-09-18 修：原来块头 entmake 写死 '(4 . "") 直接清空。）

;; 串里最后一个逗号的位置，没有则 nil
(defun gkc:lastcomma (s / i r)
  (setq i 1 r nil)
  (while (<= i (strlen s))
    (if (= (substr s i 1) ",") (setq r i))
    (setq i (1+ i))
  )
  r
)

;; 按【字节】在 s 里找 ASCII 子串 pat，回 1 基字节下标（找不到 nil）。
;;   ★ 不用 vl-string-search：它回 0 基、串里带中文时索引单位还未必是字节，
;;   而 substr 一律按字节 —— 两套混用会错位。这里自己走字节，
;;   只用来定位 "of=" / "slots=" / "slotrows=" / "|" 这类 ASCII 标记。
(defun gkc:bfind (s pat / i n m r)
  (setq i 1 n (strlen s) m (strlen pat) r nil)
  (while (and (null r) (<= i (- n m -1)))
    (if (= (substr s i m) pat) (setq r i))
    (setq i (1+ i))
  )
  r
)

;; "键=" 后面那段值的区间 -> (值首字节下标 值后第一个字节下标)，均 1 基
(defun gkc:kvspan (r key / b e n)
  (setq b (gkc:bfind r key) n (strlen key))
  (if b
    (progn
      (setq e (gkc:bfind (substr r (+ b n)) "|"))
      (list (+ b n) (if e (+ b n e -1) (1+ (strlen r))))
    )
    nil
  )
)

;; 元数据串维护（只动三处，其余一字不改地带走）：
;;   pairs = ((旧块名 . 新块名) ...) —— 只用于 of= 的精确改名
;;   delta = +K 增 K 槽 / -K 减 K 槽 / 0 不动
;;         —— 改 slots 数值 + slotrows 补 / 去 K 项
(defun gkc:metafix (desc pairs delta / r sp v w n)
  (setq r desc)
  (if (and r (/= r ""))
    (progn
      ;; of= 精确改名：取 of= 的完整值，**等于**某个旧名才换。
      ;; 别用 vl-string-subst 做子串替换 —— 柜块名互为前缀时（「开关柜」对
      ;; 「开关柜-高压」）会把 of=开关柜-高压 误改成 of=开关柜-AH1-高压。
      (setq sp (gkc:kvspan r "of="))
      (if sp
        (progn
          (setq v (substr r (car sp) (- (cadr sp) (car sp))))
          (foreach pr pairs
            (if (and (car pr) (cdr pr) (= v (car pr)))
              (setq v (cdr pr))
            )
          )
          (setq r (strcat (substr r 1 (1- (car sp)))
                          v (substr r (cadr sp))))
        )
      )
      (if (/= delta 0)
        (progn
          ;; slots=NN —— 槽数
          (setq sp (gkc:kvspan r "slots="))
          (if sp
            (progn
              (setq v (atoi (substr r (car sp) (- (cadr sp) (car sp)))))
              (setq v (max 1 (+ v delta)))
              (setq r (strcat (substr r 1 (1- (car sp)))
                              (itoa v) (substr r (cadr sp))))
            )
          )
          ;; slotrows=1,2,3 —— 每槽行数；新槽是空槽 = 1 行，增 K 槽补 K 项、
          ;;   减 K 槽去 K 项（一项都不能少，否则 MCP 侧按它推的槽高会错位）
          (setq sp (gkc:kvspan r "slotrows="))
          (if sp
            (progn
              (setq v (substr r (car sp) (- (cadr sp) (car sp))))
              (if (> delta 0)
                (progn
                  (setq n 0)
                  (while (< n delta)
                    (setq v (strcat v ",1"))
                    (setq n (1+ n))
                  )
                )
                (progn
                  (setq n (- delta))
                  (while (> n 0)
                    (setq w (gkc:lastcomma v))
                    (if w (setq v (substr v 1 (1- w))))
                    (setq n (1- n))
                  )
                )
              )
              (setq r (strcat (substr r 1 (1- (car sp)))
                              v (substr r (cadr sp))))
            )
          )
        )
      )
    )
  )
  r
)

;; ================================================================
;; 五、定义侧：克隆重建（增 / 减一行）
;; ================================================================

;; 把点 p 的 y 换成 ny，z 有就留着、没有也不硬塞
;;   LWPOLYLINE 的顶点是 2D 点 (x y)，硬补一个 nil 会让 entmake
;;   报「DXF 组不正确: (10 0.0 -6.0 nil)」—— 踩过。
(defun gkc:setY (p ny)
  (cons (car p) (cons ny (cddr p)))
)

;; entmake 一个图元（去掉句柄 / 所有者这类会冲突的组码）
(defun gkc:emit (ed / out q)
  (setq out nil)
  (foreach q ed
    (if (not (member (car q) '(5 330 102 360)))
      (setq out (cons q out))))
  (entmake (reverse out))
)

;; 给「局部 y < B」的点整体 ±K*P；不需要动的原样返回（B 那条底线本身不动）
;;   K 省略 = 1（老调用方一个字节都不用改）
(defun gkc:yshift (ed mode B p k / need out q pt dy)
  (setq k (if (and k (> k 0)) k 1))
  (setq dy (if (= mode "A") (- (* p k)) (* p k)) need nil)
  (foreach q ed
    (if (and (member (car q) '(10 11)) (listp (cdr q)) (numberp (car (cdr q))))
      (if (< (cadr (cdr q)) (- B 1e-6)) (setq need T))))
  (if (not need)
    ed
    (progn
      (setq out nil)
      (foreach q ed
        (if (and (member (car q) '(10 11)) (listp (cdr q)) (numberp (car (cdr q))))
          (progn
            (setq pt (cdr q))
            (if (< (cadr pt) (- B 1e-6))
              (setq q (cons (car q) (gkc:setY pt (+ (cadr pt) dy)))))))
        (setq out (cons q out)))
      (reverse out)))
)

;; 行区分栏竖线（如「规格 | 数量」之间那根）：下端一律应当落在【行区
;;   底线】上。行区底线移动多少、它下端就跟着移多少 ——
;;     增 N 行：下端 -> B - N*P（不跟就会缺：新槽那一段没有竖线）
;;     减 N 行：下端 -> B + N*P（不跟就会拖到已删掉的行区里去）
;;   上端（行区顶）一律不动：加槽只往行区底部加，行区顶不挪。
;;   判据 = 「竖线（LINE、两端 x 相等）穿过了槽位行」：y 区间里落得下
;;   至少一个槽的 y。用这条而不是「下端 == B」是有原因的 —— 早期版本
;;   扩容时压根没管竖线，图上已经留下「下端落后若干个行距」的块，等值
;;   判据救不回来；「穿过槽位行」把这一段历史欠账一次补齐。
;;   ★ 必须放在 yshift 之后调。yshift 只挪「严格低于 B」的点，下端正好
;;     == B 的那一端它一个字节都不碰；顺序反过来 vfix 先改好的端点会被
;;     yshift 当成「低于 B 的点」再挪一次（增行变下移 2N 个行距）。
(defun gkc:vslot? (sls lo hi / hit)
  (setq hit nil)
  (foreach s sls
    (if (and (>= (cadr s) lo) (<= (cadr s) hi)) (setq hit T)))
  hit
)

(defun gkc:vfix (ed mode B p k sls / x1 y1 x2 y2 lo hi nlo out q)
  (if (/= "LINE" (cdr (assoc 0 ed)))
    ed
    (progn
      (setq k (if (and k (> k 0)) k 1))
      (setq x1 (cadr (assoc 10 ed)) y1 (caddr (assoc 10 ed))
            x2 (cadr (assoc 11 ed)) y2 (caddr (assoc 11 ed)))
      (setq lo (min y1 y2) hi (max y1 y2))
      (if (and (equal x1 x2 1e-6) (> hi (+ B 0.01)) (gkc:vslot? sls lo hi))
        (progn
          (setq nlo (if (= mode "A") (- B (* p k)) (+ B (* p k))))
          (setq out nil)
          (foreach q ed
            (cond
              ;; 只动【下端】那一端：它的 y 就是 lo。上端（hi）一个字不碰。
              ;; ★ 比 y 要用 (caddr q) —— q 是带组码的 (10 x y z)，
              ;;   写成 (caddr (cdr q)) 取到的是 z=0.0，判据永不成立，
              ;;   于是整条线被逐元素原样重建 = 看着像"没命中"（踩过）。
              ((and (= 10 (car q)) (listp (cdr q)) (equal (caddr q) lo 1e-6))
               (setq out (cons (cons 10 (gkc:setY (cdr q) nlo)) out)))
              ((and (= 11 (car q)) (listp (cdr q)) (equal (caddr q) lo 1e-6))
               (setq out (cons (cons 11 (gkc:setY (cdr q) nlo)) out)))
              (T (setq out (cons q out)))
            )
          )
          (reverse out)
        )
        ed
      )
    )
  )
)

;; 减 K 行时要丢掉的图元：
;;   ① 最底 K 槽（槽号 maxn-K+1 .. maxn）的全部 ATTDEF；
;;   ② 行区最底 K 条横线 —— B, B+P, ..., B+(K-1)P。
;;      （行区横线自底线 B 起向上每 P 一条，所以最底 K 条就是这个集合。）
;;   K 省略 = 1 —— 与改前「只删槽 maxn + 只删 B 那条线」完全等价。
(defun gkc:drop? (ed mode B maxn k / ty s lo j y hit)
  (if (/= mode "D")
    nil
    (progn
      (setq k (if (and k (> k 0)) k 1))
      (setq ty (cdr (assoc 0 ed)) lo (- maxn k -1))
      (cond
        ((= ty "ATTDEF")
         (setq s (gkc:slotno (cdr (assoc 2 ed))))
         (if (and s (>= s lo) (<= s maxn)) T nil))
        ((= ty "LINE")
         (if (equal (caddr (assoc 10 ed)) (caddr (assoc 11 ed)) 1e-6)
           (progn
             (setq y (caddr (assoc 10 ed)) hit nil)
             (setq j 0)
             (while (and (< j k) (null hit))
               (if (equal y (+ B (* j p)) 0.01) (setq hit T))
               (setq j (1+ j))
             )
             hit
           )
           nil
         ))
        (T nil))
    )
  )
)

;; 复制一条 ATTDEF 给新槽：tag 换号、默认值清空、点按 dy 平移
(defun gkc:mkat (d nnew dy / tg sfx out q pt)
  (setq tg (cdr (assoc 2 d)) sfx (gkc:suffix tg))
  (setq out nil)
  (foreach q d
    (cond
      ((member (car q) '(5 330 102 360)) nil)
      ((= 2 (car q)) (setq out (cons (cons 2 (gkc:mktag nnew sfx)) out)))
      ((= 3 (car q)) (setq out (cons (cons 3 (gkc:mktag nnew sfx)) out)))
      ((= 1 (car q)) (setq out (cons (cons 1 "") out)))
      ((and (member (car q) '(10 11)) (listp (cdr q)))
       (setq pt (cdr q))
       (setq out (cons (cons (car q) (gkc:setY pt (+ (cadr pt) dy))) out)))
      (T (setq out (cons q out)))
    )
  )
  (reverse out)
)

;; 复制一条线到新的 y
(defun gkc:mkline (d newy / out q pt)
  (setq out nil)
  (foreach q d
    (cond
      ((member (car q) '(5 330 102 360)) nil)
      ((and (member (car q) '(10 11)) (listp (cdr q)))
       (setq pt (cdr q))
       (setq out (cons (cons (car q) (gkc:setY pt newy)) out)))
      (T (setq out (cons q out)))
    )
  )
  (reverse out)
)

;; 重建一个「已经增减过 K 行」的新定义
;;   mode = "A" 增 / "D" 减；K 省略 = 1（与改前逐字等价）
;;   返回 (新定义名 新最大槽号 新槽ATTDEF列表)，失败返回 nil
(defun gkc:rebuild (bn newbn mode pairs k / bh base flags desc g0 B p maxn sls low hl addl newdefs ed d2 res j)
  (setq g0 (gkc:geo bn))
  (if (null g0)
    nil
    (progn
      (setq k (if (and k (> k 0)) k 1))
      (setq B (car g0) p (cadr g0) maxn (caddr g0) sls (nth 3 g0))
      (setq low (nth 4 g0) hl (nth 5 g0))
      (setq addl nil newdefs nil)
      (if (= mode "A")
        (progn
          ;; ① 最底槽那一套 ATTDEF 复制 K 份 —— 第 j 份给新槽 maxn+j，
          ;;    整体下移 j 个行距（j=1 那轮就是改前的那一次，逐字一致）
          (setq j 0)
          (while (< j k)
            (setq j (1+ j))
            (foreach ed (caddr low)
              (setq d2 (gkc:mkat ed (+ maxn j) (- (* p j))))
              (setq newdefs (cons d2 newdefs))
              (setq addl (cons d2 addl))
            )
            ;; ② 行区底线那条横线复制 K 条到 B-P, B-2P, ... B-K*P
            ;;    （各新槽的底线；B 那条原地留用，变成最上那个新槽的顶线）
            (if hl (setq addl (cons (gkc:mkline hl (- B (* p j))) addl)))
          )
        )
      )
      (setq bh (entget (tblobjname "BLOCK" bn)))
      (setq base (cdr (assoc 10 bh)) flags (cdr (assoc 70 bh)))
      ;; 原定义的 Comments（MCP 侧自描述串）必须带走 —— 见 gkc:metafix
      (setq desc (gkc:metafix (cdr (assoc 4 bh)) pairs (if (= mode "A") k (- k))))
      (entmake (list '(0 . "BLOCK") '(100 . "AcDbEntity") '(8 . "0")
                     '(100 . "AcDbBlockBegin") (cons 2 newbn) (cons 3 newbn)
                     ;; 70 的 bit2 = 「含非常量属性定义」——少了它，_.-INSERT
                     ;; 插这个定义出来一个属性都不带（实测踩过），必须补上
                     (cons 70 (logior (if flags flags 0) 2))
                     (cons 10 base) (cons 4 (if desc desc ""))))
      (foreach ed (gkc:ents bn)
        (if (not (gkc:drop? ed mode B maxn k))
          ;; 先 yshift（底部区整体平移），再把分栏竖线下端吸附到新的行区底线
          (gkc:emit (gkc:vfix (gkc:yshift ed mode B p k) mode B p k sls))
        )
      )
      (foreach ed addl (gkc:emit ed))
      (entmake '((0 . "ENDBLK") (100 . "AcDbEntity") (8 . "0") (100 . "AcDbBlockEnd")))
      (list newbn (+ maxn k) (reverse newdefs))
    )
  )
)

;; ================================================================
;; 六、主逻辑
;; ================================================================

;; 公共准备：算本排、按定义分组、算几何、查槽数一致
;;   返回 (pinfo groups maxn) 或 nil（pinfo 为 ((块名 B P 槽表 参照列表) ...)）
(defun gkc:prep (e row / snap gs pinfo nset g0)
  (if (null row) (setq row (gkc:row e (gkc:snapshot))))
  (if (null row)
    nil
    (progn
      (setq gs (gkc:groups row) pinfo nil)
      (foreach g gs
        (setq g0 (gkc:geo (car g)))
        (if g0 (setq pinfo (cons (list (car g) (car g0) (cadr g0) (nth 3 g0) (cdr g))
                                 pinfo))))
      (if (null pinfo)
        nil
        (progn
          (setq nset (mapcar '(lambda (z) (apply 'max (mapcar 'car (nth 3 z)))) pinfo))
          (list (reverse pinfo) gs nset)
        )
      )
    )
  )
)

;; ---------- 增 ----------
;; K 省略 = 1（老交互路径与改前一致）
(defun gkc:add (e row k / pr pinfo gs nset rep maxn nnew g nb B p r newbn res cnt pairs oh nh mapped)
  (setq k (if (and k (> k 0)) k 1))
  (setq rep "" mapped nil pairs nil)
  (setq pr (gkc:prep e row))
  (cond
    ((null pr) (setq rep (strcat SEP "[GKC] 选中的不是属性块，或本排没有槽位属性块 —— 退出。")))
    (T
     (setq pinfo (car pr) gs (cadr pr) nset (caddr pr))
     (setq rep (strcat SEP "[GKC] 整排增 " (itoa k) " 槽 —— 本排 " (itoa (length pinfo)) " 个块定义"
                       (if (apply '= nset)
                         ""
                         (strcat "（各块槽数不同，以下各按自身现有槽数分别 +" (itoa k) "，互不影响）"))))
     ;; 先把本排各定义的新名一次性算好（映射表）—— rebuild 要拿它把 meta 里的
     ;; of=（表头块指向柜块）一起改名。必须一次算完：等第一组建好新定义后
     ;; gkc:newname 再查重就会给出带 (1) 的名字，两块的名字就对不上了。
     (setq pairs nil)
     (foreach g pinfo
       (setq pairs (cons (cons (car g) (gkc:newname (car g) (car (nth 4 g)))) pairs))
     )
     (setq pairs (reverse pairs))
     (foreach g pinfo
       (setq nb (car g) B (cadr g) p (caddr g) r (nth 4 g))
       (setq maxn (apply 'max (mapcar 'car (nth 3 g))) nnew (+ maxn k))
       (setq newbn (cdr (assoc nb pairs)))
       (setq res (gkc:rebuild nb newbn "A" pairs k))
       (if res
         (progn
            (setq cnt 0)
            ;; 旧句柄必须在 newref 之前取 —— 它内部会把旧参照 entdel 掉。
            ;; 收集成 (旧句柄 新句柄 新块名)：MCP 侧靠它改写写入目标。
            (foreach x r
              (setq oh (cdr (assoc 5 (entget x))))
              (setq nh (gkc:newref x newbn nil))
              (if nh
                (progn
                  (setq cnt (1+ cnt))
                  (setq mapped (cons (list oh nh newbn) mapped))
                )
              )
            )
           (setq rep (strcat rep SEP "  [" nb "] 槽 " (itoa maxn) " -> " (itoa nnew)
                             "；新定义 " newbn
                             "；同步 " (itoa cnt) " 个参照（重造，句柄已变）"
                             "；底部区下移 " (rtos (* p k) 2 2)))
         )
         (setq rep (strcat rep SEP "  [" nb "] 定义重建失败，本块未动"))
       )
     )
     (setq rep (strcat rep SEP "[GKC] 完成。整排已 +" (itoa k) " 槽（各块按自身槽数分别计算），量一下图框是否有空间放高出来的部分。"))
    )
  )
  (gkc:say rep)
  ;; (报告串 参照映射 定义映射)
  ;;   参照映射 = ((旧句柄 新句柄 新块名) ...)   —— MCP 侧按它改写写入目标
  ;;   定义映射 = ((旧块名 . 新块名) ...)        —— MCP 侧按它重认 block / header
  (list rep (reverse mapped) (reverse pairs))
)

;; ---------- 减 ----------
;; K 省略 = 1（老交互路径与改前一致）
(defun gkc:del (e row k / pr pinfo gs nset rep minn bad g nb B p r tags newbn res cnt kv maxn pairs oh nh mapped)
  (setq k (if (and k (> k 0)) k 1))
  (setq rep "" mapped nil pairs nil)
  (setq pr (gkc:prep e row))
  (cond
    ((null pr) (setq rep (strcat SEP "[GKC] 选中的不是属性块，或本排没有槽位属性块 —— 退出。")))
    (T
     (setq pinfo (car pr) gs (cadr pr) nset (caddr pr))
     (setq minn (apply 'min nset))
     (cond
       ;; 减 K 槽后剩下的必须还有 *gkc:min* 个（K=1 时与改前那条 <= 完全等价）
       ((< (- minn k) *gkc:min*)
        (setq rep (strcat SEP "[GKC] 本排至少有一个块只剩 " (itoa minn) " 个槽位，减 "
                          (itoa k) " 个就到下限以下了，拒绝（下限 "
                          (itoa *gkc:min*) "）。")))
       (T
        ;; 闸门：整排每个块各自最底 K 槽的任意属性有非空值 -> 整次拒绝
        (setq bad nil)
        (foreach g pinfo
          (setq maxn (apply 'max (mapcar 'car (nth 3 g))))
          (foreach x (nth 4 g)
            (foreach tg (gkc:slot-tags-r (car g) (- maxn k -1) maxn)
              (setq kv (gkc:trim (gkc:tag x tg)))
              (if (/= kv "")
                (setq bad (cons (list (car g) (cdr (assoc 2 (entget x))) tg kv) bad))
              )
            )
          )
        )
        (if bad
          (setq rep (strcat SEP "[GKC] 减被拒绝 —— 本排至少一个块的最底 " (itoa k)
                            " 个槽还有数据，按规矩一个块都不动。共 " (itoa (length bad)) " 处：" SEP
                            (apply 'strcat
                                   (mapcar '(lambda (z)
                                              (strcat "   [" (car z) "] 句柄 " (cadr z)
                                                      "  " (caddr z) " = " (cadddr z) SEP))
                                           (reverse bad)))))
          (progn
            (setq rep (strcat SEP "[GKC] 整排减 " (itoa k) " 槽 —— 本排 " (itoa (length pinfo)) " 个块定义"
                              (if (apply '= nset)
                                (strcat "，删最底 " (itoa k) " 槽（槽号 " (itoa (- (car nset) k -1))
                                        ".." (itoa (car nset)) "，已确认该段全空）")
                                (strcat "（各块槽数不同，各自删自身最底 " (itoa k)
                                        " 槽，已确认该段全空）"))))
            ;; 新名映射一次算完（理由同 gkc:add —— rebuild 要拿它改 meta 的 of=）
            (setq pairs nil)
            (foreach g pinfo
              (setq pairs (cons (cons (car g) (gkc:newname (car g) (car (nth 4 g)))) pairs))
            )
            (setq pairs (reverse pairs))
            (foreach g pinfo
              (setq nb (car g) B (cadr g) p (caddr g) r (nth 4 g))
              (setq maxn (apply 'max (mapcar 'car (nth 3 g))))
              (setq tags (gkc:slot-tags-r nb (- maxn k -1) maxn))
              (setq newbn (cdr (assoc nb pairs)))
              (setq res (gkc:rebuild nb newbn "D" pairs k))
              (if res
                (progn
                    (setq cnt 0)
                    (foreach x r
                      (setq oh (cdr (assoc 5 (entget x))))
                      (setq nh (gkc:newref x newbn tags))
                      (if nh
                        (progn
                          (setq cnt (1+ cnt))
                          (setq mapped (cons (list oh nh newbn) mapped))
                        )
                      )
                    )
                  (setq rep (strcat rep SEP "  [" nb "] 槽 " (itoa maxn) ".."
                                    (itoa (- maxn k -1)) " 已删（"
                                    (itoa (length tags)) " 条属性）"
                                    "；新定义 " newbn
                                    "；同步 " (itoa cnt) " 个参照（重造，句柄已变）"
                                    "；底部区上移 " (rtos (* p k) 2 2)))
                )
                (setq rep (strcat rep SEP "  [" nb "] 定义重建失败，本块未动"))
              )
            )
            (setq rep (strcat rep SEP "[GKC] 完成。整排已 -" (itoa k) " 槽（各块按自身槽数分别计算）。"))
          )
        )
       )
     )
    )
  )
  (gkc:say rep)
  ;; (报告串 参照映射 定义映射) —— 口径同 gkc:add
  (list rep (reverse mapped) (reverse pairs))
)

;; ================================================================
;; 七、按句柄扩容（MCP 导入工具专用入口）
;; ================================================================
;; 谁找块：MCP 侧。attkit import 比对差异时，导入模板里本来就有块名 /
;;         柜号 / 句柄，AI 从差异里直接就知道「哪一排、要加几个槽」。
;;         所以这一节【不做几何识别来挑块】，只做「按给定参照 + 给定
;;         槽数，一次扩到位」；但给进来的参照会先过一遍 gkc:rowfill，
;;         把「紧密相接的一整行」补齐（见下）。
;;
;; 两个入口（都能被 acad_run_lisp 直接调）：
;;   (gkc:plan   "332,35B,384,3AD,3D6,3FF,428" 2)   只读清单，图不动；返回报告串
;;       （两者都先按几何补齐整行；漏给的句柄会被自动纳入并点名）
;;   (gkc:expand "332,35B,384,3AD,3D6,3FF,428" 2)   执行；返回
;;       "[GKC-RESULT]报告…|@defs=旧名>新名;…|@refs=旧柄>新柄>新块名;…|@bad=…"
;;       MCP 侧靠 @refs 改写写入目标（句柄全变）、靠 @defs 重认块名
;;       （扩容后本排参照换成「原名-柜号」，旧名字一个参照都找不到了）
;;   K 给负数 = 减槽（减的闸门照旧：该段有值就整次拒绝）
;;
;; ★ 一次只传【一排】的句柄。两排万一共用同一个块定义，一起传会把两排
;;   并成一个新定义（新定义名只取一个柜号）—— 想处理两排就调两次。
;;
;; 句柄少给几个【按几何自动补】：整行（同 y 带 + x 相接）一块不落。
;; 以前不补，只给半排句柄就静默只扩一半 —— 高低压紧贴成一行时最典型：
;; 给低压 4 个句柄，高压两块原地不动、底边错开一个行距，而 plan 的
;; 「漏参照」自检只比同名块定义，一条警告都不出（2026-09-18 踩到）。
;; 补齐后报告里点名新纳入的块；传的句柄横跨两排时两排都会被纳入。
;; —— 两排共用【同一个块定义】时仍要小心：一起传会把两排并成一个新
;; 定义（新定义名只取一个柜号），这种情况分两次调。

;; 句柄串 "332,35B" 或 ("332" "35B") -> 句柄字符串列表
(defun gkc:tokens (s / res cur i ch)
  (if (listp s)
    s
    (progn
      (setq res nil cur "" i 1)
      (while (<= i (strlen s))
        (setq ch (substr s i 1))
        (if (or (= ch ",") (= ch ";") (= ch " "))
          (progn
            (if (/= cur "") (setq res (cons cur res)))
            (setq cur "")
          )
          (setq cur (strcat cur ch))
        )
        (setq i (1+ i))
      )
      (if (/= cur "") (setq res (cons cur res)))
      (reverse res)
    )
  )
)

;; 句柄串 -> (实体名列表 无效句柄列表)
;;   句柄是本机唯一稳的定位方式：柜号改了不怕，但重造参照后句柄必变。
(defun gkc:refs-from (s / res bad h e)
  (setq res nil bad nil)
  (foreach h (gkc:tokens s)
    (setq e (handent h))
    (if (and e (= "INSERT" (cdr (assoc 0 (entget e)))))
      (setq res (cons e res))
      (setq bad (cons h bad))
    )
  )
  (list (reverse res) (reverse bad))
)

;; 参照列表里有没有这个句柄
(defun gkc:inh (h lst / r)
  (setq r nil)
  (foreach e lst
    (if (= h (cdr (assoc 5 (entget e)))) (setq r T))
  )
  r
)

;; 本排被哪个块整包住（就是图框）？返回 (下边距 图框块名)，算不出 nil。
;;   下边距 = 本排最低边 - 图框最低边。扩槽让块往下长，它就变小 ——
;;   变成负数就是破框，所以要在动手【之前】报出来。
;;   包住本排的块可能不止一个（外框套内框），取面积最小的那个。
(defun gkc:clearance (refs / x0 y0 x1 y1 bb e snap best mn2 mx2 o2 ar a1 a2)
  (setq x0 1e9 y0 1e9 x1 -1e9 y1 -1e9)
  (foreach e refs
    (setq bb (gkc:bb e))
    (if bb
      (progn
        (if (< (car (car bb)) x0) (setq x0 (car (car bb))))
        (if (< (cadr (car bb)) y0) (setq y0 (cadr (car bb))))
        (if (> (car (cadr bb)) x1) (setq x1 (car (cadr bb))))
        (if (> (cadr (cadr bb)) y1) (setq y1 (cadr (cadr bb))))
      )
    )
  )
  (if (> x0 x1)
    nil
    (progn
      (setq snap (gkc:snapshot) best nil ar nil)
      (foreach o2 snap
        (setq mn2 (cadr o2) mx2 (caddr o2))
        (if (and (<= (car mn2) (+ x0 0.01)) (>= (car mx2) (- x1 0.01))
                 (<= (cadr mn2) (+ y0 0.01)) (>= (cadr mx2) (- y1 0.01)))
          (progn
            (setq a1 (* (- (car mx2) (car mn2)) (- (cadr mx2) (cadr mn2))))
            (if (or (null best) (< a1 ar))
              (progn (setq best o2 ar a1))
            )
          )
        )
      )
      (if best
        (list (- y0 (cadr (cadr best))) (cdr (assoc 2 (entget (car best)))))
        nil
      )
    )
  )
)

;; 只读预演：列出将动哪些定义、槽数怎么变、块底移多少、离图框还剩多少。
;;   全用只读调用（gkc:bb / gkc:snapshot / handent），图一个字节都不动。
(defun gkc:plan (s k / kk rf refs bad f1 addd pr pinfo rep g nb r maxn all nall i e2 miss cl pv after)
  (setq kk (if (and k (/= k 0)) k 1))
  (setq rf (gkc:refs-from s) refs (car rf) bad (cadr rf))
  (setq rep (strcat "[GKC 预演] 拟 " (if (> kk 0) "+" "") (itoa kk) " 槽；只读，图不会动。"))
  (if bad
    (setq rep (strcat rep SEP "  无效句柄 " (itoa (length bad)) " 个：" (gkc:join bad ","))))
  ;; 先按几何补齐整行（只读）：手动口单点走的就是 gkc:row，MCP 口以前
  ;; 不走 —— 只给半排句柄就静默只扩一半，故这里补上，并把补进来的点名。
  (setq f1 (gkc:rowfill refs) refs (car f1) addd (cadr f1))
  (if refs
    (setq rep (strcat rep SEP "  句柄 " (itoa (- (length refs) (length addd)))
                      " 个 → 按几何补齐整行 " (itoa (length refs)) " 个"
                      (if addd
                        (strcat "；补进来的 " (itoa (length addd)) " 个："
                                (gkc:join
                                  (mapcar '(lambda (x) (strcat (cdr (assoc 5 (entget x))) "="
                                                               (cdr (assoc 2 (entget x)))))
                                          addd) " "))
                        "（给的就是整行）"))))
  (cond
    ((null refs)
     (setq rep (strcat rep SEP "  没有有效参照，没法继续。")))
    (T
     (setq pr (gkc:prep (car refs) refs))
     (if (null pr)
       (setq rep (strcat rep SEP "  给出的参照里没有带槽位的属性块"
                         "（认的是块定义里的「" *gkc:pfx* "NN」属性）—— 没法扩容。"))
       (progn
         (setq pinfo (car pr))
         (setq pv (caddr (car pinfo)))
         (foreach g pinfo
           (setq nb (car g) r (nth 4 g) maxn (apply 'max (mapcar 'car (nth 3 g))))
           (setq rep (strcat rep SEP "  [" nb "] 槽 " (itoa maxn) " -> " (itoa (+ maxn kk))
                             "；行距 " (rtos (caddr g) 2 2)
                             "；块底" (if (> kk 0) "下移 " "上移 ")
                             (rtos (abs (* (caddr g) kk)) 2 2)
                             "；重造 " (itoa (length r)) " 个参照（句柄会变）"))
           ;; 同定义的参照有没有漏在清单外
           (setq all (ssget "X" (list '(0 . "INSERT") (cons 2 nb))))
           (setq nall (if all (sslength all) 0) miss 0 i 0)
           (while (< i nall)
             (setq e2 (ssname all i))
             (if (not (gkc:inh (cdr (assoc 5 (entget e2))) r)) (setq miss (1+ miss)))
             (setq i (1+ i))
           )
           (if (> miss 0)
             (setq rep (strcat rep SEP "      ! 同定义还有 " (itoa miss)
                               " 个参照没在清单里 —— 它们会留在旧定义上，槽数跟本排对不上")))
         )
         (setq cl (gkc:clearance refs))
         (if cl
           (progn
             (setq after (- (car cl) (* pv kk)))
             (setq rep (strcat rep SEP "  图框 [" (cadr cl) "] 下边距 "
                               (rtos (car cl) 2 2) " -> " (rtos after 2 2)))
             (if (< after 0.0)
               (setq rep (strcat rep SEP "      ! 扩完会破框（低于图框下边 "
                                 (rtos (abs after) 2 2) "）—— 先挪框 / 改图幅，别急着加")))
           )
           (setq rep (strcat rep SEP "  没找到包住本排的图框，破框与否自己看图"))
         )
       )
     )
    )
  )
  (gkc:say rep)
  rep
)

;; 执行：按句柄对整排一次扩 K 槽（K 负 = 减）。
;; 返回【定界字符串】而不是 LISP 表 —— acad_run_lisp 是用 vl-princ-to-string
;; 把结果写文件回传的，直接回表会变成带转义引号的打印格式，Python 侧没法读。
;; 格式（人读报告在前，|@ 开头的是机器段）：
;;   [GKC-RESULT]报告…|@defs=旧块名>新块名;…|@refs=旧句柄>新句柄>新块名;…|@bad=句柄,…
(defun gkc:expand (s k / kk rf refs bad f1 addd frep row raw res rep mapped pairs out)
  (setq kk (if (and k (/= k 0)) k 1))
  (setq rf (gkc:refs-from s) refs (car rf) bad (cadr rf))
  (setq rep "" mapped nil pairs nil frep "")
  ;; 补齐整行（口径同 plan）—— 只给半排句柄时以前静默只扩一半
  (setq f1 (gkc:rowfill refs) refs (car f1) addd (cadr f1))
  (if addd
    (setq frep (strcat "[GKC] 按几何补齐整行：新纳入 " (itoa (length addd)) " 个（"
                       (gkc:join
                         (mapcar '(lambda (x) (strcat (cdr (assoc 5 (entget x))) "="
                                                      (cdr (assoc 2 (entget x)))))
                                 addd) " ")
                       "）" SEP)))
  (cond
    ((null refs)
     (setq rep "[GKC] 没有有效参照（句柄无效或已删除），图没动。"))
    (T
     (setq row refs)
     ;; 静默执行；quiet 的恢复放在 vl-catch-all-apply 之后 ——
     ;; add/del 内部报错也不会把全局开关留在 T 上（否则下次手动调用就哑了）。
     (setq *gkc:quiet* T)
     (setq raw (vl-catch-all-apply
                 (if (> kk 0) 'gkc:add 'gkc:del)
                 (list (car row) row (if (> kk 0) kk (- kk)))))
     (setq *gkc:quiet* nil)
     (if (vl-catch-all-error-p raw)
       (setq rep (strcat "[GKC] 执行报错，图可能只改了一部分 —— 核对后重来："
                         (vl-catch-all-error-message raw)))
       (setq res raw rep (car res) mapped (cadr res) pairs (caddr res))
     )
    )
  )
  (setq out (strcat "[GKC-RESULT]" frep rep
                    "|@defs=" (if pairs
                                (apply 'strcat
                                       (mapcar '(lambda (z) (strcat (car z) ">" (cdr z) ";"))
                                               pairs))
                                "")
                    "|@refs=" (if mapped
                                (apply 'strcat
                                       (mapcar '(lambda (z)
                                                  (strcat (car z) ">" (cadr z) ">" (caddr z) ";"))
                                               mapped))
                                "")
                    "|@bad=" (if bad (gkc:join bad ",") "")))
  out
)

;; ================================================================
;; 八、命令外壳
;; ================================================================
;; 列出本排 → 问增减 → 执行
(defun gkc:go (e row / k r x n)
  (if (null row)
    (princ "\n没认到本排的槽位属性块，退出。")
    (progn
      (princ "\n【本排将影响的块】")
      (setq r 0)
      (foreach x row
        (setq r (1+ r))
        (princ (strcat "\n   " (itoa r) ") " (cdr (assoc 2 (entget x)))
                      "   柜号=" (gkc:trim (gkc:tag x "柜号"))))
      )
      (princ (strcat "\n   共 " (itoa (length row)) " 个块。"))
      (initget "A D X")
      (setq k (getkword "\n[增(A) / 减(D) / 退出(X)] <增>: "))
      (cond
        ((= k "X") (princ "\n已退出，图没动。"))
        (T
         (setq n (getint (strcat "\n" (if (= k "D") "减" "增") "几个槽 <1>: ")))
         (setq n (if (and n (> n 0)) n 1))
         (if (= k "D") (gkc:del e row n) (gkc:add e row n))
        )
      )
    )
  )
)

(defun c:GKC ( / ss e row x i)
  (princ "\n[GKC] 柜排槽位增减 —— 在本排行区底部一次增 / 减 N 个标准槽位行")
  (princ "\n       作用范围：本排【全部】属性块，含表头块。点一个块 → 自动认段。")
  (princ "\n       也可以一次多选 / 框选本排若干块 —— 那就完全按你选的来，不再自动认。")
  (princ "\n       （为什么要确认范围：高压排与低压排非槽属性完全一样，槽数一变就可能被认成一段。）")
  (princ "\n       增(A)：新槽落在行区最底 → 备注行 / 容量功率行整体下移 N 个行距，块底向下长。")
  (princ "\n       减(D)：删掉行区最底 N 槽 → 备注行 / 容量功率行整体上移 N 个行距，块底向上收。")
  (princ "\n       柜顶（顶部数据容器）与已有槽位一律不动；表头块与柜块始终对齐。")
  (princ "\n       减的闸门：本排任意一个块、最底 N 槽任意一个属性有数据 → 整次拒绝，一个块都不动。")
  (princ "\n       块定义会克隆成新名（原名-柜号）再改，原定义原封不动，别的排不受影响。")
  (princ "\n       本排参照会重造一遍（句柄会变）—— 本机 CAD 没法给旧参照补属性，只有重插才带得出来。")
  (princ "\n       执行前会把将影响的块列出来，看清了再动手。")
  (princ "\n       被导入工具调用时走另一条口（按句柄直达，并自动按几何补齐整行）：")
  (princ "\n           (gkc:plan \"句柄,句柄,...\" N)    只读清单，图不动")
  (princ "\n           (gkc:expand \"句柄,句柄,...\" N)  执行")
  (princ "\n选择本排任意一个柜块或表头块（可多选）<退出>: ")
  (setq ss (ssget '((0 . "INSERT"))))
  (cond
    ((null ss) (princ "\n没选到块，退出。"))
    ((> (sslength ss) 1)
     ;; 多选 = 显式指定本排
     (setq row nil i 0)
     (while (< i (sslength ss))
       (setq x (ssname ss i))
       (if (gkc:maxslot (cdr (assoc 2 (entget x))))
         (setq row (cons x row))
         (princ (strcat "\n  略过（无槽位属性）：" (cdr (assoc 2 (entget x))))))
       (setq i (1+ i))
     )
     (setq row (reverse row))
     (gkc:go (car row) row)
    )
    (T
     (setq e (ssname ss 0))
     (gkc:go e (gkc:row e (gkc:snapshot)))
    )
  )
  (princ)
)

(princ "\n[属性块-槽位增减] 已加载，命令：GKC（选本排任一块或直接多选本排 → 增 A / 减 D）")
(princ)


;;; ================================================================
;;; 模块 二、属性块-增加行高.lsp（GH，命令 GGH）
;;; ================================================================

;;; ============================================================
;;; 属性块-增加行高.lsp                                      命令：GGH
;;; ------------------------------------------------------------
;;; 作用
;;;   某个槽的「规格」一行写不下（如变压器 35 字），把这一槽在行区
;;;   里加高 M 行 —— 全排（柜块 + 表头块）的同一个槽统一变高。
;;;   槽号不动、槽数不动，块只往下长。
;;;
;;; 为什么要单独一个文件
;;;   「槽位增减」(GKC) 管【槽数】，「增加行高」管【单槽几行】，是
;;;   两件事。填数方算出行数后要「先加高、后写值」，这一步需要能
;;;   单独调用，故独立成命令。
;;;   重建内核（克隆定义 / 重造参照 / 元数据维护）完全复用 GKC ——
;;;   见 gh:ensure，本文件会自己把 GKC load 进来。
;;;
;;; 与 GKC 的关键差别（别混）
;;;   GKC 加槽：在行区【底部】加全新的槽（槽号 +1、标签整体换号）。
;;;   GGH 加行：在【某个已有槽的内部】加行（槽号不变，标签由
;;;             元件NN规格 长成 元件NN规格1 / 规格2 …）。
;;;
;;; 几何口径（全部实测得来，不写死数字）
;;;   ① 槽 01 在最上、maxn 在最下，槽间距 P，行区底线 B。
;;;   ② 加行是【向下长】：槽 s 的第 1 行原地不动，长出来的行把槽 s
;;;      以下的一切（更靠下的槽 / 底部区 / 柜框底边）整体往下推，
;;;      块顶不动 —— 块因此变高；而铺图按【几何顶】对位，所以柜顶
;;;      位置不变。
;;;   ③ 块定义是【全排共享】的：改一个槽 = 本排所有参照（柜块与
;;;      表头块）这一槽一起变高。这就是"统一增加" —— 不需要、也
;;;      没法只改某一个参照。
;;;   ④ 表头块没有「规格」属性：行数【数不出来】（gh:cur 恒 0），所以
;;;      它不自己算，一律沿用柜块算出的整排基准 da —— 只跟着长行格、
;;;      不添字（见 gh:baseda）。第一遍加行时表头自算恰好等于真值，
;;;      再调一次就会多长一遍，这是必须避开的地方。
;;;      两段因此天然等高，不用配平。
;;;
;;; ★ 统一变换（一条公式管住全部图元类型）
;;;   一个点的下移量 = Σ(下边界 >= y 的各槽的加行数) * P
;;;   其中 槽 s 的下边界 = B + (maxn - s) * P
;;;   用 >= 而不是 > 是关键：正好压在下边界上的横线（还有行区底线
;;;   上的分栏竖线下端）必须把自己那一槽的加行量也一起算，否则它会
;;;   比新底线高出一行。槽属性自身 y = 下边界 + off（off>0），不受
;;;   这条影响。
;;;   （加高时不新增横线：槽内不画分隔线，只补「规格N」属性。）
;;;   ⑤ 加高槽里【没分行的数据】（数量 / 名称 / 型号）垂直居中：
;;;      槽变高后槽顶不动、槽底往下 dy*P，槽的垂直中点就下移 dy*P/2。
;;;      这些单行数据 = 先随槽按统一公式下移（gh:sh），再额外下移
;;;      dy*P/2（gh:shdn），保持它在格里原来的相对位置，所以不管
;;;      对正方式是基线 / 中间 / 顶，都仍然居中。规格类不居中 ——
;;;      它本来就按行一格格往下排。
;;;   一条公式同时管住：槽属性 / 行区横线 / 竖线两端 / 柜参数区 /
;;;   底部区 / 柜框矩形（底边下移、顶边不动 = 自动变高）。
;;;
;;; 三个入口
;;;   ① 手动：命令 GGH —— 点本排任一属性块，输入每槽行数（逗号
;;;      分隔，如 1,1,1,1,1,3,1；回车 = 全 1）。
;;;   ② 被填数方调用：
;;;        (gh:apply "句柄,句柄" "1,1,1,1,1,3,1,1")  批量，一次到位
;;;        (gh:slot  "句柄,句柄" 6 3)                单槽：第 6 槽变 3 行
;;;        (gh:dry   "句柄,句柄" "1,1,1,1,1,3,1,1")  只读预演，图不动
;;;   ③ 返回 (报告 参照映射 定义映射)，与 gkc:expand 同形；报告头
;;;      带 [GGH-RESULT] 与 |@defs / |@refs / |@bad 机器段。
;;;
;;; ★ 句柄会变
;;;   重建后参照被重造（本机 COM 无 AddAttribute，只能靠 _. -INSERT
;;;   让 CAD 自己实例化属性），句柄全变 —— 所以【先加高、再填值】
;;;   时，填值方要用返回的新句柄。要加多个槽就一次把 plan 传完，
;;;   别循环调 gh:slot（每调一次句柄变一轮）。
;;;
;;; 编码：ANSI/GBK 无 BOM
;;; 依赖：属性块-槽位增减.lsp（内核），本文件会自动 load
;;; ============================================================
(vl-load-com)
(if (null SEP) (setq SEP (chr 10)))

;; ---------------- 依赖（槽位增减的内核） ----------------
(setq gh:dep "D:/kk三部曲/148.CAD插件研究/lisp/属性块-槽位增减.lsp")

;; 内核不在就 load 一次。返回 T / nil。
;;   ★ 不在这里 princ：MCP 口是拿 vl-princ-to-string 把结果整串回传的，
;;     中途 princ 会污染回包；要报错由调用方报。
(defun gh:ensure ( / p)
  (if gkc:rebuild
    T
    (progn
      (setq p (vl-catch-all-apply 'load (list gh:dep)))
      (if (and (not (vl-catch-all-error-p p)) gkc:rebuild) T nil)
    )
  )
)

;; ================================================================
;; 一、行数：计划 / 现状
;; ================================================================

;; 槽 n 的目标行数；plan 可以是表 (1 3 1)、逗号串 "1,3,1"、或 nil（全 1）
(defun gh:at (plan n / v)
  (cond
    ((null plan) 1)
    ((listp plan)
     (setq v (nth (1- n) plan))
     (if (and v (numberp v) (> v 0)) (fix v) 1))
    (T
     (setq v (nth (1- n) (gkc:tokens plan)))
     (if v (max 1 (atoi v)) 1))
  )
)

;; 该槽现在占几行（数 元件NN规格 / 规格1 / 规格2 …）
;;   表头块的槽位是「名称 / 型号」，没有规格属性 —— 数出来恒为 0。
;;   所以调用方必须自己取【max 1 _】：表头也是"本来就有 1 行"，
;;   只是没有规格属性可以数（见 gh:rebuild 里的注释）。
(defun gh:cur (bn n / k ed sfx)
  (setq k 0)
  (foreach ed (gkc:attdefs bn)
    (if (= (gkc:slotno (cdr (assoc 2 ed))) n)
      (progn
        (setq sfx (gkc:suffix (cdr (assoc 2 ed))))
        (if (= (substr sfx 1 4) "规格") (setq k (1+ k)))
      )
    )
  )
  k
)

;; 某个块定义按行计划要加几行 -> ((槽号 . 加行数) ...)，没有要加的 nil
(defun gh:deltas (bn plan / g0 sls s da n dy)
  (setq g0 (gkc:geo bn))
  (if (null g0)
    nil
    (progn
      (setq sls (nth 3 g0) da nil)
      (foreach s sls
        (setq n (car s)
              ;; 现状行数【下限是 1】：表头块没有「规格」属性（gh:cur 恒 0），
              ;; 但它的槽本来就有 1 行 —— 直接拿 gh:cur 当现状，表头就会按
              ;; 「从 0 行加到 N 行」算，9 个槽全被加满（Σ=12 行），整块被撑爆。
              ;; 表头要的正是「只长行格、不添字」：行数跟柜块一样多。
              dy (- (gh:at plan n) (max 1 (gh:cur bn n))))
        (if (/= dy 0) (setq da (cons (cons n dy) da)))
      )
      (reverse da)
    )
  )
)

;; 块定义有没有「规格」类槽位属性
;;   柜块有（规格 / 规格1…），表头块没有（它的槽位是 名称 / 型号）。
;;   这个区别很关键：gh:cur 数不出表头的行数（恒 0），所以表头不能
;;   自己算 da，必须沿用柜块的 —— 见 gh:baseda。
;;   ★ 必须先判 gkc:slotno 非 nil（也就是 tag 是「元件NN…」）：
;;     表头块有个「主母线规格」属性，而 gkc:suffix 是「从第 7 字节截到
;;     尾」—— 主母线规格 正好 10 字节，截完剩「规格」两个字，于是不判
;;     槽号就会把表头当成"有规格的块"，基准 da 取错、整排多长一遍。
;;     （gh:cur 里有槽号判断所以没中招，这里一开始漏了。）
(defun gh:hasspec (bn / ed tg r)
  (setq r nil)
  (foreach ed (gkc:attdefs bn)
    (setq tg (cdr (assoc 2 ed)))
    (if (and (gkc:slotno tg) (= (substr (gkc:suffix tg) 1 4) "规格"))
      (setq r T))
  )
  r
)

;; 整排的基准加行表 -> (找到了吗 da表)
;;   ★ 为什么不能逐块自算：
;;     表头块没有「规格」属性 -> gh:cur 恒 0 -> 它按「从 0 行加到 N 行」
;;     算，比真值大。第一遍加行时两者恰好相等（柜块也从 0 起），所以
;;     第一遍看不出问题；再调一次就露馅：柜块 dy=0 不动，表头又加一遍，
;;     整排被拉成不等高。
;;   ★ 口径：全排统一 —— 拿【有规格属性的块】（柜块）算出来的 da 当作
;;     整排基准，表头照它执行。柜块能数准，两段又同步，所以表头与柜块
;;     永远等高（这正是"表头高度由槽数定义"的落地方式）。
;;   整排一个能数的块都没有（纯表头排）-> (nil nil)，退回逐块自算。
(defun gh:baseda (gs plan / da g found)
  (setq da nil found nil)
  (foreach g gs
    (if (and (null found) (gh:hasspec (car g)))
      (progn (setq da (gh:deltas (car g) plan) found T))
    )
  )
  (list found da)
)

;; 整排加行计划的总加行数（用于算块底下移 / 新块高）
(defun gh:sig (da / s t2)
  (setq t2 0)
  (foreach s da (setq t2 (+ t2 (cdr s))))
  t2
)

;; ================================================================
;; 二、统一变换（把「加几行」落到每个点上）
;; ================================================================

;; 点 y 的下移量（统一公式）
;;   bots = 每槽【实测底线】((槽号 . 底线y) ...)，块定义坐标
;;   ★ 不能再按 B + P*(maxn-s) 现推：那条式子暗含「每槽都是 1 行」，
;;     块一旦加过行（槽6 三行 / 槽1 两行），推出的底线整体偏低，
;;     居中会连带偏掉（2026-09-20 实测：数量少抬 1.5）。
(defun gh:dy (y bots P da / tot s dl)
  (setq tot 0.0)
  (foreach s bots
    (setq dl (cdr (assoc (car s) da)))
    (if (and dl (/= dl 0) (>= (cdr s) (- y 1e-6)))
      (setq tot (+ tot (* P dl))))
  )
  tot
)

;; 按统一公式平移一个实体的所有 10/11 点
(defun gh:sh (ed bots P da / out q pt)
  (setq out nil)
  (foreach q ed
    (if (and (member (car q) '(10 11)) (listp (cdr q)) (numberp (car (cdr q))))
      (progn
        (setq pt (cdr q))
        (setq out (cons (cons (car q)
                              (gkc:setY pt (- (cadr pt)
                                              (gh:dy (cadr pt) bots P da))))
                         out)))
      (setq out (cons q out))
    )
  )
  (reverse out)
)

; 每槽【实测底线】-> ((槽号 . 底线y) ...)，块定义坐标
;;   sls = gkc:slots 的结果 ((槽号 最小属性y ATTDEF表) ...)
;;   ★ 属性 y = 格底 + 半字高（原块的设计就是「文字在格内垂直居中」，
;;     不是贴格底）—— 所以 底线 = 该槽最小属性 y - 半字高。
(defun gh:bots (sls / r h)
  (setq r nil)
  (foreach s sls
    (setq h (cdr (assoc 40 (car (caddr s)))) h (if h h 3.0))
    (setq r (cons (cons (car s) (- (cadr s) (/ h 2.0))) r))
  )
  (reverse r)
)

;; 把实体的 10/11 点 y 整体再下移 d（两点同量，10/11 的相对关系不变）
;;   ★ 居中不能「直接把 10/11 都设成同一个 y」：对正不是基线时，
;;     实际落点由 11 点（对齐点）决定，10 点只是左基线，两者本来就差
;;     约半个字高；都设成同一值会让文字整体偏 h/2（中间对正）或 h（顶对正）。
(defun gh:shdn (ed d / out q)
  (setq out nil)
  (foreach q ed
    (if (and (member (car q) '(10 11)) (listp (cdr q)) (numberp (car (cdr q))))
      (setq out (cons (cons (car q) (gkc:setY (cdr q) (- (cadr (cdr q)) d))) out))
      (setq out (cons q out))
    )
  )
  (reverse out)
)

;; meta 的 slotrows= 重写成新的完整列表（槽数没变，只换每槽行数）
(defun gh:meta (desc plan maxn / r sp v i)
  (setq r desc)
  (if (and r (/= r ""))
    (progn
      (setq sp (gkc:kvspan r "slotrows="))
      (if sp
        (progn
          (setq v "" i 1)
          (while (<= i maxn)
            (setq v (strcat v (if (= v "") "" ",") (itoa (gh:at plan i))))
            (setq i (1+ i))
          )
          (setq r (strcat (substr r 1 (1- (car sp))) v (substr r (cadr sp))))
        )
      )
    )
  )
  r
)

;; 把参照上某槽的属性 tag 从 oldsfx 改成 newsfx（只动组码 2：迁值按 tag 认）
;;   gkc:newref 迁值是「按 tag 配对」的 —— 定义侧把 元件NN规格 改成了
;;   元件NN规格1，参照这一侧不跟着改，值就会静默丢掉。失败要能改回来，
;;   所以 old / new 都给。
(defun gh:relabel (e da oldsfx newsfx / sub ed tg n nt d2)
  (setq sub (entnext e))
  (while (and sub (= "ATTRIB" (cdr (assoc 0 (setq ed (entget sub))))))
    (setq tg (cdr (assoc 2 ed)) n (gkc:slotno tg))
    (if (and n (= (gkc:suffix tg) oldsfx) (cdr (assoc n da)))
      (progn
        (setq nt (gkc:mktag n newsfx) d2 nil)
        (foreach q ed
          (setq d2 (cons (if (= (car q) 2) (cons 2 nt) q) d2))
        )
        (entmod (reverse d2))
      )
    )
    (setq sub (entnext sub))
  )
)

;; 参照侧按 da 的方向改 tag（2026-09-24 增，为「减行」）：
;;   dy > 0 的槽：规格 -> 规格1（加行）
;;   dy < 0 且目标 1 行：规格1 -> 规格（减回单行形态）
;;   rev = T 时是回滚：新参照重造失败，把上面做过的翻回去。
;;   为什么不能直接调两次 gh:relabel：两次都按同一个 da
;;   条件命中，第二次会把第一次改好的又改回去。
(defun gh:relabel-dh (e da plan rev / sub ed tg n nt d2 dl tgt su)
  (setq sub (entnext e))
  (while (and sub (= "ATTRIB" (cdr (assoc 0 (setq ed (entget sub))))))
    (setq tg (cdr (assoc 2 ed)) n (gkc:slotno tg) nt nil)
    (if (and n (cdr (assoc n da)))
      (progn
        (setq dl (cdr (assoc n da)) tgt (gh:at plan n) su (gkc:suffix tg))
        (cond
          (rev
           (cond
             ((and (> dl 0) (= su "规格1")) (setq nt (gkc:mktag n "规格")))
             ((and (< dl 0) (= tgt 1) (= su "规格"))
              (setq nt (gkc:mktag n "规格1")))
           )
          )
          (T
           (cond
             ((and (> dl 0) (= su "规格")) (setq nt (gkc:mktag n "规格1")))
             ((and (< dl 0) (= tgt 1) (= su "规格1"))
              (setq nt (gkc:mktag n "规格")))
           )
          )
        )
        (if nt
          (progn
            (setq d2 nil)
            (foreach q ed (setq d2 (cons (if (= (car q) 2) (cons 2 nt) q) d2)))
            (entmod (reverse d2))
          )
        )
      )
    )
    (setq sub (entnext sub))
  )
)

;; ================================================================
;; 三、重建定义（槽号、槽数都不变，只让指定槽变高）
;; ================================================================

;; 返回 (新定义名 da表)；没有要改的槽 -> nil
;;   da0 = 'AUTO 自算 / 一张 da 表（整排基准，见 gh:baseda）/
;;         nil（整排都不用动，直接判无变化）
(defun gh:rebuild (bn newbn plan da0 / g0 B P maxn sls da addl dell bh base flags desc hb
                     ed d2 d3 s n dy tg hing y0 y0p j j0 nt c0 yb mid su m0
                     bots)
  (setq g0 (gkc:geo bn))
  (if (null g0) nil
    (progn
      (setq B (car g0) P (cadr g0) maxn (caddr g0) sls (nth 3 g0))
      ;; 每槽底线由属性反推，只用来给各点分「下移档」（gh:dy）。
      ;; 这样块加过行之后再改 plan 也不会算错（旧写法按「每槽 1 行」现推）。
      ;; 居中不再依赖它（见下面 gh:shdn）。
      (setq bots (gh:bots sls))
      (setq da (if (eq da0 'AUTO) (gh:deltas bn plan) da0))
      (if (null da) nil
        (progn
          ;; --- 备好要新增的实体 ---
          (setq addl nil dell nil)
          (foreach s sls
            (setq n (car s) dy (cdr (assoc n da)))
            (if (and dy (> dy 0))
              (progn
                ;; ① 槽内【不再】新增横线（加高只让槽变高、只补规格属性）。
                ;;   这里只算两个基准供下面 ② 定位新属性用：
                ;;   y0  = 该槽原下边界；y0p = 该槽加高后的新下边界
                (setq y0 (cdr (assoc n bots)))
                (setq y0p (- y0 (gh:dy y0 bots P da)))
                ;; ② 槽的「规格」属性复制 dy 份（表头块没有规格 -> 只长格不添字）
                ;;   ★ hing 取【规格类属性里最靠上的那个】（y 最大），不能只认
                ;;     后缀恰好等于「规格」：槽一旦加过行，属性就叫 规格1 /
                ;;     规格2 / 规格3，单行的「规格」不复存在 —— 只认它就会
                ;;     一个也找不到，于是行格长了、属性却没补，槽里永远少最后
                ;;     一行（2026-09-20 实测：槽6 加高后只有 规格1/2/3）。
                (setq c0 (max 1 (gh:cur bn n)))
                (setq hing nil yb -1e99)
                (foreach ed (caddr s)
                  (setq tg (cdr (assoc 2 ed)))
                  (if (and (= (substr (gkc:suffix tg) 1 4) "规格")
                           (> (caddr (assoc 10 ed)) yb))
                    (progn (setq hing ed) (setq yb (caddr (assoc 10 ed)))))
                )
                (if hing
                  (progn
                    (setq j 0)
                    (while (< j dy)
                      (setq j (1+ j))
                      ;; 位移一次算到【最终坐标】：gkc:mkat 的相对位移是按原
                      ;; 几何加的，而 addl 里的实体不再过 gh:sh，所以必须自己
                      ;; 把全局下移量算进去。
                      ;;   hing 是本槽【顶行】那个规格属性（第 1 行）。设它原有
                      ;;   y = y0+off，它自己的下移量 = rowdy(y0+off)，而
                      ;;   rowdy(y0) = rowdy(y0+off) + dy*P（y0 比顶行低，多含
                      ;;   本槽自己），于是 rowdy(y0+off) = (y0 - y0p) - dy*P。
                      ;;   新属性是【第 (c0+j) 行】：第 m 行的 y = 顶行y - P*(m-1)。
                      ;;   合计相对位移 = -rowdy(y0+off) - P*(c0+j-1)
                      ;;                = (y0p - y0) + P*(dy - (c0+j-1))
                      ;;   c0=1 时退化成原来的 P*(dy-j) —— 与首轮加行逐字等价。
                      ;;   j=dy 时落在本槽新底线之上（底线+off）。
                      (setq d2 (gkc:mkat hing n (+ (- y0p y0)
                                                   (* P (- dy (- (+ c0 j) 1))))))
                      (setq nt (gkc:mktag n (strcat "规格" (itoa (+ c0 j)))))
                      (setq d3 nil)
                      (foreach q d2
                        (setq d3 (cons (if (member (car q) '(2 3)) (cons (car q) nt) q) d3))
                      )
                      (setq addl (cons (reverse d3) addl))
                    )
                  )
                )
              )
            )
            ;; ★ 减行（2026-09-24 增）：该槽多出来的「规格N」登记为待删，
            ;;   重建定义时不写进新定义。参照侧那些旧属性不必单独删 ——
            ;;   gkc:newref 是「按 tag 配对迁值」，新定义里没有的 tag
            ;;   自然迁不过去，旧参照被整只重造。
            (if (and dy (< dy 0))
              (progn
                (setq j0 (1+ (gh:at plan n)) m0 (max 1 (gh:cur bn n)))
                (while (<= j0 m0)
                  (setq dell (cons (gkc:mktag n (strcat "规格" (itoa j0))) dell))
                  (setq j0 (1+ j0))
                )
              )
            )
          )
          ;; --- 重建定义 ---
          (setq bh (entget (tblobjname "BLOCK" bn)))
          (setq base (cdr (assoc 10 bh)) flags (cdr (assoc 70 bh)))
          (setq desc (gh:meta (cdr (assoc 4 bh)) plan maxn))
          ;; ★ 块头建不出来就【绝不往下灌】：block 与 ENDBLK 之间的那批 entmake
          ;;   一旦没有块上下文，会直接落进模型空间，变成几十个散图元 ——
          ;;   而且 entmake 只返回 nil、不报错，表面看"图没动"，其实图上多了
          ;;   一堆东西（2026-09-20 实测：newbn 不合法时整块内容漏进模型空间）。
          (setq hb (entmake (list '(0 . "BLOCK") '(100 . "AcDbEntity") '(8 . "0")
                                  '(100 . "AcDbBlockBegin")
                                  (cons 2 newbn) (cons 3 newbn)
                                  ;; 70 的 bit2 = 「含非常量属性定义」——少了它，
                                  ;; _. -INSERT 插这个定义出来一个属性都不带
                                  (cons 70 (logior (if flags flags 0) 2))
                                  (cons 10 base) (cons 4 (if desc desc "")))))
          (if (null hb)
            (progn
              (gkc:say (strcat SEP "  [" bn "] 新定义块头建不出来（newbn="
                              (if newbn newbn "nil") "），本块没动。"))
              nil)
            (progn
              (foreach ed (gkc:ents bn)
                (setq d2 ed d3 nil mid nil)
                ;; 单行「规格」跟着改名 -> 规格1（定义侧这一步不做，参照就配不上）
                (if (and (= "ATTDEF" (cdr (assoc 0 d2)))
                         (member (cdr (assoc 2 d2)) dell))
                  (setq d2 nil)
                )
                (if (and d2 (= "ATTDEF" (cdr (assoc 0 d2))))
                  (progn
                    (setq tg (cdr (assoc 2 d2)) n (gkc:slotno tg))
                    ;; 单行「规格」<->「规格1」双向改名（定义侧不改，参照就配不上）
                    ;;   加行：目标 > 1 且当前「规格」 -> 规格1
                    ;;   减行：目标 = 1 且当前「规格1」 -> 规格
                    (if (and n (cdr (assoc n da)))
                      (progn
                        (setq su (gkc:suffix tg) nt nil)
                        (cond
                          ((and (> (gh:at plan n) 1) (= su "规格"))
                           (setq nt (gkc:mktag n "规格1")))
                          ((and (= (gh:at plan n) 1) (= su "规格1"))
                           (setq nt (gkc:mktag n "规格")))
                        )
                        (if nt
                          (progn
                            (foreach q d2
                              (setq d3 (cons (if (member (car q) '(2 3)) (cons (car q) nt) q) d3))
                            )
                            (setq d2 (reverse d3) tg nt)
                          )
                        )
                      )
                    )
                    ;; ★ 加高槽里【没分行的数据】（数量 / 名称 / 型号）垂直居中。
                    ;;   做法：保持它在原格里的相对位置不变 ——
                    ;;     ① 先按统一公式随槽下移（gh:sh，10/11 点一起动）；
                    ;;     ② 再额外下移本槽新增高度的一半（dy*P/2）。
                    ;;   原理：槽顶不动、槽底下移 dy*P，槽的垂直中点就下移 dy*P/2；
                    ;;   文字原来在格里怎么居中，就还怎么居中 —— 与对正方式
                    ;;   （基线 / 中间 / 顶）、字高 h 与行距 P 的比例都无关，
                    ;;   全程不用字高、也不用槽的上下边界线。
                    ;;   ★ 不能再用「新中点 - 半字高」现算目标 y，并把 10/11 都设成
                    ;;     同一个值：那只在【基线对正】时才对，且抹掉了 10/11 的关系。
                    ;;   ★ 规格类不居中：规格 1..N 本来就按行一格格往下排。
                    (if (and n (/= (substr (gkc:suffix tg) 1 4) "规格")
                             (cdr (assoc n da)))
                      (progn
                        (setq d2 (gh:sh d2 bots P da))
                        (setq d2 (gh:shdn d2 (/ (* P (cdr (assoc n da))) 2.0)))
                        (setq mid T)
                      )
                    )
                  )
                )
                (if d2 (gkc:emit (if mid d2 (gh:sh d2 bots P da))))
              )
              (foreach ed addl (gkc:emit ed))
              (entmake '((0 . "ENDBLK") (100 . "AcDbEntity") (8 . "0") (100 . "AcDbBlockEnd")))
              (list newbn da)
            )
          )
        )
      )
    )
  )
)

;; ================================================================
;; 四、只读预演
;; ================================================================

;; 列一遍：哪些槽会加几行、块底再下移多少、块高新旧。
;;   全走只读调用（gkc:refs-from / gkc:rowfill / gkc:groups / gkc:geo /
;;   gkc:bb），图一个字节都不动。
(defun gh:dry (s plan / rf refs bad f1 addd rep gs g nb da bd B P maxn t2
                 mx e0 bb h0 h1)
  (if (null (gh:ensure))
    (strcat SEP "[GGH] 内核没就位：" gh:dep "（先 load 属性块-槽位增减.lsp）")
    (progn
      (setq rep "" )
      (setq rf (gkc:refs-from s) refs (car rf) bad (cadr rf))
      (setq f1 (gkc:rowfill refs) refs (car f1) addd (cadr f1))
      (cond
        ((null refs)
         (setq rep (strcat SEP "[GGH] 预演：没有有效参照（句柄无效或已删除）。")))
        (T
         (setq rep (strcat SEP "[GGH] 预演（图没动）"
                           (if addd
                             (strcat SEP "  按几何补齐整行：新纳入 " (itoa (length addd)) " 个")
                             "")))
         (setq gs (gkc:groups refs))
         ;; 与 gh:apply 同口径：表头沿用柜块的基准 da，不自己算
         (setq bd (gh:baseda gs plan))
         (foreach g gs
           (setq nb (car g)
                 da (if (car bd) (cadr bd) (gh:deltas nb plan)))
           (if da
             (progn
               (setq B (car (gkc:geo nb)) P (cadr (gkc:geo nb))
                     maxn (caddr (gkc:geo nb)) t2 (gh:sig da))
               ;; 块高新旧：拿本组首参照的包围盒量
               (setq e0 (cadr g) bb (gkc:bb e0) h0 nil h1 nil)
               (if bb
                 (progn
                   (setq h0 (- (cadr (cadr bb)) (cadr (car bb)))
                         h1 (+ h0 (* P t2)))))
               (setq rep (strcat rep SEP "  [" nb "] 加行 "
                                 (gkc:join
                                   (mapcar '(lambda (z) (strcat (itoa (car z)) "槽+"
                                                                (itoa (cdr z))))
                                           da) " ")
                                 "（共 " (itoa t2) " 行）"
                                 "；块底再下移 " (rtos (* P t2) 2 1)
                                 (if h0 (strcat "，块高 " (rtos h0 2 1)
                                                " -> " (rtos h1 2 1)) ""))))
             (setq rep (strcat rep SEP "  [" nb "] 不用动（行数与现状一致）")))
         )
        )
      )
      (if bad
        (setq rep (strcat rep SEP "  无效句柄：" (gkc:join bad ","))))
      rep
    )
  )
)

;; ================================================================
;; 五、主入口
;; ================================================================

;; 按行计划重建本排（给一个句柄也会按几何补齐整排）
;;   s    = 句柄串 / 句柄表
;;   plan = 每槽行数（表或 "1,3,1,2" 串；长度按最大槽号取，缺的按 1）
;;   返回 (报告 参照映射 定义映射) —— 与 gkc:expand 同形
(defun gh:apply (s plan / rf refs bad f1 addd frep rep mapped pairs gs g bd
                   nb r newbn res cnt oh nh da ok emsg)
  (if (null (gh:ensure))
    (list (strcat SEP "[GGH] 内核没就位：" gh:dep
                  "（先 load 属性块-槽位增减.lsp）") nil nil)
    (progn
      (setq rep "" mapped nil pairs nil frep "")
      (setq rf (gkc:refs-from s) refs (car rf) bad (cadr rf))
      (setq f1 (gkc:rowfill refs) refs (car f1) addd (cadr f1))
      (if addd
        (setq frep (strcat "[GGH] 按几何补齐整行：新纳入 " (itoa (length addd)) " 个；"))
      )
      (cond
        ((null refs)
         (setq rep "[GGH] 没有有效参照（句柄无效或已删除），图没动。"))
        (T
         (setq gs (gkc:groups refs))
         ;; 整排基准 da：拿柜块算，表头照它执行（见 gh:baseda）
         (setq bd (gh:baseda gs plan))
         ;; 新定义名一次算完 —— 等第一组建好再算，gkc:newname 会给带 (1) 的名字
         (foreach g gs
           (setq pairs (cons (cons (car g) (gkc:newname (car g) (cadr g))) pairs))
         )
         (setq pairs (reverse pairs))
         (foreach g gs
           (setq nb (car g) r (cdr g) newbn (cdr (assoc nb pairs)))
           ;; 每组单独兜住 —— 一组炸了不许把后面的组和回包一起吞掉
           (setq res (vl-catch-all-apply 'gh:rebuild
                                         (list nb newbn plan
                                               (if (car bd) (cadr bd) 'AUTO))))
           (cond
             ((vl-catch-all-error-p res)
              (setq rep (strcat rep SEP "  [" nb "] 重建报错，本组跳过："
                                (vl-catch-all-error-message res))))
             ((null res)
              (setq rep (strcat rep SEP "  [" nb "] 没动（行数与现状一致，或块头没建出来）")))
             (T
              (setq da (cadr res))
              ;; 先改参照标签 -> newref 按 tag 迁值才匹配得上
              (foreach x r (gh:relabel-dh x da plan nil))
              (setq cnt 0 ok 0 emsg "")
              (foreach x r
                (setq oh (cdr (assoc 5 (entget x))))
                (setq nh (vl-catch-all-apply 'gkc:newref (list x (car res) nil)))
                (cond
                  ((vl-catch-all-error-p nh)
                   (gh:relabel-dh x da plan T)
                   (setq ok (1+ ok))
                   (if (= emsg "") (setq emsg (vl-catch-all-error-message nh))))
                  ((null nh)
                   ;; 重造失败 -> 标签改回去，别把旧参照弄成孤儿属性
                   (gh:relabel-dh x da plan T)
                   (setq ok (1+ ok)))
                  (T
                   (setq cnt (1+ cnt))
                   (setq mapped (cons (list oh nh (car res)) mapped)))
                )
              )
              (setq rep (strcat rep SEP "  [" nb "] 加行 "
                                (gkc:join
                                  (mapcar '(lambda (z) (strcat (itoa (car z)) "槽+"
                                                               (itoa (cdr z))))
                                          (reverse da)) " ")
                                "；新定义 " (car res)
                                "；同步 " (itoa cnt) " 个参照（重造，句柄已变）"
                                (if (> ok 0) (strcat "；" (itoa ok)
                                                     " 个重造失败已回滚"
                                                     (if (= emsg "") ""
                                                       (strcat "（" emsg "）")))
                                  "")))
             )
           )
         )
        )
      )
      (gkc:say rep)
      ;; (报告 参照映射 定义映射)
      (list (strcat "[GGH-RESULT]" frep rep
                    "|@defs=" (if pairs
                                (apply 'strcat
                                       (mapcar '(lambda (z)
                                                  (strcat (car z) ">" (cdr z) ";"))
                                               pairs))
                                "")
                    "|@refs=" (if mapped
                                (apply 'strcat
                                       (mapcar '(lambda (z)
                                                  (strcat (car z) ">" (cadr z) ">"
                                                          (caddr z) ";"))
                                               mapped))
                                "")
                    "|@bad=" (if bad (gkc:join bad ",") ""))
            (reverse mapped) (reverse pairs))
    )
  )
)

;; 单槽：只让第 n 槽到 rows 行（其余槽保持现状）
;;   gh:rebuild 只处理「目标行数 > 现状」的槽，所以 plan 里其余位填 1
;;   不会把已经加高的槽缩回去。
;;   ★ 每调一次句柄全变；要改多个槽就自己拼好 plan 一次调 gh:apply。
(defun gh:slot (s n rows / rf refs mx i bn pl)
  (if (null (gh:ensure))
    (list (strcat SEP "[GGH] 内核没就位：" gh:dep) nil nil)
    (progn
      (setq rf (gkc:refs-from s) refs (car rf))
      (if (null refs)
        (list (strcat SEP "[GGH] 没有有效参照，图没动。") nil nil)
        (progn
          (setq refs (car (gkc:rowfill refs)))
          (setq mx 0)
          (foreach e refs
            (setq bn (cdr (assoc 2 (entget e))))
            (setq i (gkc:maxslot bn))
            (if (and i (> i mx)) (setq mx i))
          )
          (setq pl nil i 1)
          (while (<= i mx)
            (setq pl (cons (if (= i n) rows 1) pl))
            (setq i (1+ i))
          )
          (gh:apply s (reverse pl))
        )
      )
    )
  )
)

;; ================================================================
;; 六、命令外壳
;; ================================================================

;; 点一个块 -> 问每槽行数 -> 重建
(defun c:GGH ( / e s pl r)
  (if (null (gh:ensure))
    (princ (strcat SEP "内核没就位：" gh:dep))
    (progn
      (setq e (car (entsel (strcat SEP "选本排任一槽位属性块: "))))
      (if (null e)
        (princ (strcat SEP "没选，退出。"))
        (progn
          (setq s (cdr (assoc 5 (entget e))))
          (setq pl (getstring T (strcat SEP
                                        "每槽行数（逗号分隔，如 1,1,1,1,1,3,1；回车=全 1）: ")))
          (setq r (gh:apply s pl))
          (princ (strcat SEP (car r)))
        )
      )
    )
  )
  (princ)
)

(princ)


;;; ================================================================
;;; 模块 三、属性块-箱变.lsp（XBT，命令 XBT）
;;; ================================================================

;;; ============================================================
;;; 属性块-箱变.lsp                                    命令：XBT
;;; ------------------------------------------------------------
;;; 作用
;;;   箱变（高压段 + 低压段）两段独立表的【铺图】：
;;;   头尾各一枚表头块，中间按清单顺序排柜块 —— 全程只【调用】现成块，
;;;   不生成新块型、不做 MCP 那套参数计算：
;;;       [高压表头] [G1] [BYQ] [D1] [D2] [低压表头]
;;;                  40宽        35   35   35   35      40宽
;;;   两段的区别只写在【属性值】里（铜排规格 / 电压等级不同），
;;;   块型是同一份 —— 所以两段天然等高，不需要配平（MCP 才要）。
;;;
;;;   【分段口径】清单里写几条「表头」行就是几段（表头行切段）：
;;;     表头 | TMY-50*5 | 10kV             <- 段 1（图上最左那枚）
;;;     @G1 … @BYQ …                      <- 属段 1
;;;     表头 | TMY-100*8 N80*8 | 0.4kV    <- 段 2（图上最右那枚）
;;;     @D1 … @D2 …                       <- 属段 2
;;;     · 两段【各自从第 1 槽起】编号（同一槽号在两段是不同元件）
;;;     · 槽数 = max(高压段, 低压段) —— 块定义共用，只能取两段较大者
;;;     · 表头【各写各段】：第 j 枚表头只写第 j 段的元件
;;;     · 行高计划逐槽取两段最大（同上，块定义共用）
;;;   只写 1 条表头行 -> 1 段 -> 与 KYN28 单段完全同路。
;;;
;;;   铺完调一次 GGH（gh:apply）按数据统一加行高：长规格的槽位在
;;;   同一槽里向下长行，标签变成 元件NN规格1..M（不拆到别的槽位）。
;;;   加行高【全排统一】—— 块定义是共用的，加一处就是全排。
;;;
;;;   高度不用量 —— 块高只由【总行数】定：
;;;     总行数 = 每槽行数之和 = 槽数 + 加行数
;;;     块高   = 基础高(未加行时) + 行距P × (总行数 - 槽数)
;;;            = 124 + 6 × 总行数        （本块族：15槽基础高214 / 14槽208）
;;;   表头每槽恒 1 行，对表头就是「总行数 = 槽数」——
;;;   即你说的「表头高度由槽数定义」。柜块与表头同一份行高计划
;;;   -> 同一个总行数 -> 同一个块高 -> 两段天然等高，不用配平。
;;;
;;; 清单格式：与 PLT 完全同源（同一份 txt，两个命令一起吃）
;;;     表头 | TMY-50*5 | 10kV                  <- 第 1 枚表头（最左）
;;;     @G1 | 高压进出线柜 | | | 630KVA | |
;;;     1 | 负荷开关 | FN12-12RD | 125A 31.5kA 手动电分 | 1
;;;     @BYQ | 变压器 | | | 1000KVA | |
;;;     1 | 变压器 | S13 | 1000KVA 10+/-2*2.5%/0.4kV ud%＝4 Dyn11 | 1
;;;     表头 | TMY-100*8 N80*8 PE50*5 | 0.4kV    <- 第 2 枚表头（最右）
;;;     @D1 | 低压进出线柜 | | | | |
;;;     @D2 | 电容柜 | | | | |
;;;   表头行【写在它那一段的柜之前】：表头行之后、下一条表头行之前的柜
;;;   都属这一段。表头行出现顺序 = 图上表头从左到右的顺序；
;;;   柜头行出现顺序 = 图上柜从左到右的顺序。
;;;
;;; 入口
;;;   (xbt:run "清单文本")        真铺
;;;   (xbt:dry "清单文本")        只算不铺
;;;   (xbt:runfile "清单.txt")    从 GBK 文件读
;;;   (xbt:dryfile "清单.txt")    只算不铺
;;;   命令 XBT —— 交互，问清单文件路径
;;;
;;; 依赖（都自动 load）
;;;   属性块-铺图.lsp      pgt:* 模板导入 / 插块 / 量几何 / 定槽
;;;   属性块-槽位增减.lsp  gkc:* 定槽（增减槽位）
;;;   属性块-增加行高.lsp  gh:*  加行高（gh:apply）
;;;   属性块-批量填数.lsp  plt:parse / plt:plan / plt:wrap（口径同源）
;;;   模板 dwg：图框模版 / 柜块模版 / 表头块模版 / 占位块
;;;
;;; 边界
;;;   1 一框一排：整排宽 表头40 + N*柜35 + 表头40，加左边距 35 超过框宽
;;;     420 就拒绝并报差多少（箱变一般 4~8 台，够用）
;;;   2 占位块在【加行高之后】才插 —— gh:apply 会按几何补齐整排，
;;;     占位块不是槽位块，先插进去会被卷进分组空转一轮
;;;   3 不存盘 —— 落不落盘你自己定
;;;
;;; 编码：ANSI/GBK 无 BOM
;;; ============================================================
(vl-load-com)
(if (not (boundp 'SEP)) (setq SEP (chr 10)))

(setq *xbt:padl*   35.0)   ; 表头几何左离框左（与 PGT 同口径）
(setq *xbt:padt*   14.0)   ; 柜块几何顶离框顶
(setq *xbt:phgap*   3.0)   ; 占位块几何顶离柜块几何顶
(setq *xbt:rowsmax*   9)   ; 单槽最多几行（与 MCP SLOT_FIELD_ROWS_MAX 同口径）

;; ================================================================
;; 一、依赖与小工具
;; ================================================================

;; 按名找 lsp 并 load；成 T
(defun xbt:ld (n / f p)
  (setq f (findfile (strcat n ".lsp")))
  (if (null f) (setq f (findfile (strcat "D:/kk三部曲/148.CAD插件研究/lisp/" n ".lsp"))))
  (if f
    (progn (setq p (vl-catch-all-apply 'load (list f)))
           (not (vl-catch-all-error-p p)))
    nil)
)

(defun xbt:ensure ()
  (if (not (member 'PGT:INS (atoms-family 0)))    (xbt:ld "属性块-铺图"))
  (if (not (member 'GKC:REBUILD (atoms-family 0))) (xbt:ld "属性块-槽位增减"))
  (if (not (member 'GH:APPLY (atoms-family 0)))   (xbt:ld "属性块-增加行高"))
  (if (not (member 'PLT:PLAN (atoms-family 0)))   (xbt:ld "属性块-批量填数"))
  (and (member 'PGT:INS (atoms-family 0))
       (member 'GH:APPLY (atoms-family 0))
       (member 'PLT:PLAN (atoms-family 0)))
)

;; VLA 块参照 -> 句柄（拿不到返回 nil）
(defun xbt:hd (o / r)
  (if o
    (progn
      (setq r (vl-catch-all-apply 'vlax-vla-object->ename (list o)))
      (if (vl-catch-all-error-p r) nil (cdr (assoc 5 (entget r))))
    )
    nil)
)

;; 模型空间里【块名在 names 里】的参照句柄，按插入点 x 从左到右
;;   只认柜块 / 表头块，不认 占位块、不认图框（图框是炸开的散图元）
(defun xbt:refhd (names / ss i n e bn x out)
  (setq out nil)
  (setq ss (ssget "_X" '((0 . "INSERT") (410 . "Model"))))
  (if ss
    (progn
      (setq i 0 n (sslength ss))
      (while (< i n)
        (setq e (ssname ss i))
        (setq bn (cdr (assoc 2 (entget e))))
        (if (member bn names)
          (progn
            (setq x (car (cdr (assoc 10 (entget e)))))
            (setq out (cons (cons x (cdr (assoc 5 (entget e)))) out))
          )
        )
        (setq i (1+ i))
      )
    )
  )
  (plt:hsort out)
)

;; ================================================================
;; 二、行高计划
;; ================================================================

;; 按清单算每槽需要的行数 -> "M1,M2,..."（逗号串，直接喂 gh:apply）
;;   口径（与 MCP _cabinet_slot_rows 一致）：
;;     · 空规格恒算 1 行
;;     · 有规格按【显示宽度】拆行取行数
;;     · 同一槽取【全排最大】—— 块定义是共用的，只能取最大；
;;       箱变两段独立编号时它自动等于「逐槽取两段最大」
;;     · 单槽封顶 *xbt:rowsmax* 行
(defun xbt:rowplan (cabs map pls need / pl k mx rw emv)
  (setq pl "")
  (foreach k (plt:seq 1 need)
    (setq mx 1)
    (foreach cab cabs
      (setq emv (assoc k (plt:cabget cab map pls)))
      (if emv
        (progn
          (setq rw (length (plt:wrap (nth 3 (cdr emv)) *plt:slot-col*)))
          (if (> rw mx) (setq mx rw))
        )
      )
    )
    (if (> mx *xbt:rowsmax*) (setq mx *xbt:rowsmax*))
    (setq pl (strcat pl (if (= pl "") "" ",") (itoa mx)))
  )
  pl
)

;; 计划里有没有 >1 的槽（全 1 就不必调 GGH）
(defun xbt:needrows (pl / r v)
  (setq r nil)
  (foreach v (gkc:tokens pl)
    (if (> (atoi v) 1) (setq r T))
  )
  r
)

;; 计划里的【总行数】（每槽行数之和）—— 块高就由它定
(defun xbt:rows (pl / s v)
  (setq s 0)
  (foreach v (gkc:tokens pl)
    (setq s (+ s (atoi v)))
  )
  s
)

;; 铺图前清掉【上一轮留下的、未被引用的】克隆定义
;;   gkc:newname 碰到重名会无脑加 (1)(2)(3)… —— 反复铺图就攒一堆
;;   柜块模版-排(1)(2)…。先把未引用的清掉，名字腾空，
;;   gkc:newname 每次就能拿到干净的 柜块模版-排 / 表头块模版-表头。
;;   被引用的定义会被 -PURGE 自己拒绝 —— 所以不会碰已铺好的图。
;;   返回清掉几个。
(defun xbt:purgeold ( / b nm lst k ce)
  (setq b (tblnext "BLOCK" T) lst nil)
  (while b
    (setq nm (cdr (assoc 2 b)))
    (if (and (/= nm "") (wcmatch nm "柜块模版-排*,表头块模版-表头*"))
      (setq lst (cons nm lst))
    )
    (setq b (tblnext "BLOCK"))
  )
  (setq k 0 ce (getvar "CMDECHO"))
  (setvar "CMDECHO" 0)
  (foreach nm lst
    (if (tblobjname "BLOCK" nm)
      (progn
        (command "_.-PURGE" "_B" nm "_N")
        (if (null (tblobjname "BLOCK" nm)) (setq k (1+ k)))
      )
    )
  )
  (setvar "CMDECHO" ce)
  k
)

;; ================================================================
;; 三、主流程
;; ================================================================
(defun xbt:go (tx write / ps bus vol cabs warns tb hdrs rpt
                          need pl map pls nseg segtxt ex sx dfs cabn hdrn n
                          fa ar cr hr pr fw fh hw cw crx cry hrx hry phx phy
                          ftop caby hdry phyy bx by hdrx2 i
                          h1 h2 cabx0 totw hs plan rp rl
                          cntf cnth cntc cntp hd rsum bh pit gx cpur sd)
  (if (null (xbt:ensure))
    (strcat "缺依赖（属性块-铺图 / 属性块-槽位增减 / 属性块-增加行高 / 属性块-批量填数 有一个 load 不上），"
            "没动图。")
    (progn
      (setq ps (plt:parse tx))
      (setq bus (car ps) vol (cadr ps) cabs (caddr ps)
            warns (cadddr ps) tb (nth 4 ps) hdrs (nth 5 ps) sd (nth 6 ps))
      (cond
        ((null cabs)
         (strcat "清单里没解析出柜头行（柜头行必须以 @ 开头），没动图。" SEP
                 (if warns (strcat "  " (car warns) SEP) "")))
        ((and write (null (pgt:ms)))
         "拿不到模型空间（COM 没通），没动图。")
        (T
         ;; --- 四个块定义带进本图（只加定义，不加图元）---
         (pgt:import "图框模版.dwg" "图框模版")
         (pgt:import "柜块模版.dwg" "柜块模版")
         (pgt:import "表头块模版.dwg" "表头块模版")
         (pgt:import "占位块.dwg" "占位块")
         (cond
           ((or (null (pgt:defp "图框模版")) (null (pgt:defp "柜块模版"))
                (null (pgt:defp "表头块模版")) (null (pgt:defp "占位块")))
            "四个块定义没全进到本图（模板插不进来？），没动图。")
           (T
            ;; --- 先把上轮未引用的克隆定义清掉，腾出干净名字 ---
            (setq cpur (xbt:purgeold))
            ;; --- 排槽（与 PLT 完全同一套口径）---
            ;;   清单写了几条表头行就是几段：
            ;;     1 条 -> 1 段，老路 plt:plan
            ;;     2 条 -> 2 段，各段【独立从第 1 槽起】编号，
            ;;             槽数 = max(高压段, 低压段)（块定义共用，只能取大）
            (setq nseg (length (plt:segs cabs)))
            (if (> nseg 1)
              (progn
                (setq pls (plt:planseg cabs sd) map nil need (plt:needseg pls))
              )
              (progn
                (setq pl (plt:plan cabs (plt:sdef-at sd 1))
                      map (car pl) need (cadr pl) pls nil)
              )
            )
            ;; 段摘要：段 1（槽 6） / 段 2（槽 8）
            (setq segtxt "")
            (if pls
              (foreach ex pls
                (setq segtxt (strcat segtxt (if (= segtxt "") "" "，")
                                     "段 " (itoa (car ex))
                                     "（槽 " (itoa (caddr ex)) "）"))
              )
            )
            ;; 防呆：清单写了多遍表头行却没切出第 2 段 —— 旧写法（表头行在末尾）
            (if (and hdrs (> (length hdrs) 1) (= nseg 1))
              (setq warns (append warns
                                  (list (strcat "清单写了 " (itoa (length hdrs))
                                                " 条表头行，却只切出 1 段 —— "
                                                "表头行要写在它那一段的柜之前"))))
            )
            ;; --- 定槽：按数据算出的槽数去要现成块（不等于模板槽数才克隆一次）---
            (setq dfs (pgt:defs need "柜块模版" "表头块模版"))
            (setq cabn (car dfs) hdrn (cadr dfs) n (caddr dfs))
            ;; --- 量几何 ---
            (setq fa (pgt:fanchor))
            (setq ar (if fa (pgt:rng (car fa))))
            (setq cr (pgt:rng cabn) hr (pgt:rng hdrn) pr (pgt:rng "占位块"))
            (cond
              ((null fa)
               "图框模版里找不到锚块（那个 * 开头的匿名块参照），没动图。")
              ((or (null ar) (null cr) (null hr) (null pr))
               "量不到块定义几何（图框 / 柜块 / 表头 / 占位块 有一个缺），没动图。")
              (T
               (setq fw (- (nth 2 ar) (car ar)) fh (- (nth 3 ar) (nth 1 ar)))
               (setq hw (- (nth 2 hr) (car hr)))     ; 表头块宽 40
               (setq cw (- (nth 2 cr) (car cr)))     ; 柜块宽 35
               (setq crx (car cr) cry (nth 3 cr))    ; 柜块几何 左 / 顶
               (setq hrx (car hr) hry (nth 3 hr))    ; 表头几何 左 / 顶
               (setq phx (car pr) phy (nth 3 pr))    ; 占位块几何 左 / 顶
               (setq totw (+ hw (* (length cabs) cw) hw))   ; 表头 + 柜 + 表头
               (setq bx 0.0 by 0.0)
               (setq hdrx2 (- (+ bx *xbt:padl* totw) hw))   ; 尾表头几何左
               (cond
                 ((> (+ *xbt:padl* totw) fw)
                  (strcat "装不下：整排宽 " (rtos totw 2 1)
                          " + 左边距 " (rtos *xbt:padl* 2 1)
                          " = " (rtos (+ *xbt:padl* totw) 2 1)
                          "，超过框宽 " (rtos fw 2 0) " 共 "
                          (rtos (- (+ *xbt:padl* totw) fw) 2 1)
                          " —— 柜少一点或柜块窄一点，没动图。"))
                 (T
                  ;; 与第几台无关的 y，一次算完
                  (setq ftop (+ by fh))
                  (setq caby (- ftop *xbt:padt* cry))
                  (setq hdry (- ftop *xbt:padt* hry))
                  (setq phyy (- ftop *xbt:padt* *xbt:phgap* phy))
                  ;; 行高计划：写不写都要用它出报告
                  (setq plan (xbt:rowplan cabs map pls need))
                  ;; 高度是算出来的，不是量出来的：
                  ;;   基础高 = 加行高之前量的 cr（此时块还是模板槽数 n）
                  ;;   行距P  = gkc:geo 第 2 项（本块族 6.0）
                  ;;   块高   = 基础高 + P × (总行数 - n)
                  (setq rsum (xbt:rows plan))
                  (setq gx (vl-catch-all-apply 'gkc:geo (list cabn)))
                  (if (vl-catch-all-error-p gx) (setq gx nil))
                  (setq pit (if (and gx (numberp (cadr gx))) (cadr gx) 6.0))
                  (setq bh (+ (- (nth 3 cr) (nth 1 cr)) (* pit (- rsum n))))
                  ;; 垂直余量：块只向下长，顶距固定 —— 算得到底距，不用量
                  (if (< (- fh *xbt:padt* bh) 0.0)
                    (setq warns
                          (append warns
                                  (list (strcat "块高压穿框底：块高 " (rtos bh 2 1)
                                                " + 顶距 " (rtos *xbt:padt* 2 0)
                                                " = " (rtos (+ bh *xbt:padt*) 2 1)
                                                " > 框高 " (rtos fh 2 0))))))
                  (setq cntf 0 cnth 0 cntc 0 cntp 0 h1 nil h2 nil rp nil)
                  (if write
                    (progn
                      ;; ① 图框（COM 插 + COM 炸开，框左下角在定义内要反向补偿）
                      (setq i (pgt:ins "图框模版"
                                       (list (- bx (cadr fa) (car ar))
                                             (- by (caddr fa) (nth 1 ar)))))
                      (if i (progn (setq cntf (1+ cntf)) (pgt:exp i)))
                      ;; ② 第 1 枚表头（最左 = 高压段）
                      (setq h1 (pgt:ins hdrn (list (- (+ bx *xbt:padl*) hrx) hdry)))
                      (if h1 (setq cnth (1+ cnth)))
                      ;; ③ 中间柜，按清单顺序往右排，只写柜号
                      (setq i 0)
                      (foreach cab cabs
                        (setq cabx0 (+ bx *xbt:padl* hw (* i cw)))
                        (setq hd (pgt:ins cabn (list (- cabx0 crx) caby)))
                        (if hd
                          (progn
                            (setq cntc (1+ cntc))
                            (pgt:setatt hd "柜号" (nth 0 cab))
                          )
                        )
                        (setq i (1+ i))
                      )
                      ;; ④ 第 2 枚表头（最右 = 低压段）—— 放在所有柜之后
                      (setq h2 (pgt:ins hdrn (list (- hdrx2 hrx) hdry)))
                      (if h2 (setq cnth (1+ cnth)))
                      ;; ⑤ 加行高：全排统一（块定义共用，加一处就是全排）。
                      ;;    句柄在【改名之前】按 x 从左到右取 —— 之后块名就变了。
                      ;;    gh:apply 自己会按几何补齐整排，这里给全排更清楚。
                      ;;    整段兜住：加行高出问题不该把已经铺好的图连报告一起吞掉
                      (if (xbt:needrows plan)
                        (progn
                          (setq hs "")
                          (setq rl (xbt:refhd (list cabn hdrn)))
                          (foreach hd rl
                            (setq hs (strcat hs (if (= hs "") "" ",") hd))
                          )
                          (setq rp (vl-catch-all-apply 'gh:apply (list hs plan)))
                          (if (vl-catch-all-error-p rp)
                            (setq rp (list (strcat "加行高失败（图已铺好，可单独敲 GGH 补）："
                                                   (vl-catch-all-error-message rp))))
                          )
                        )
                      )
                      ;; ⑥ 占位块 —— 放在加行高【之后】：它不是槽位块，
                      ;;    先插会被 gh:apply 的「按几何补齐整排」卷进分组空转。
                      ;;    柜块只是向下长高，几何顶没动 -> 占位块 y 依旧成立。
                      (setq i 0)
                      (foreach cab cabs
                        (setq cabx0 (+ bx *xbt:padl* hw (* i cw)))
                        (if (pgt:ins "占位块" (list (- cabx0 phx) phyy))
                          (setq cntp (1+ cntp))
                        )
                        (setq i (1+ i))
                      )
                    )
                  )
                  ;; --- 报告：只给读回结论（数量 / 落点 / 行高 / warnings）---
                  (setq rpt
                    (strcat
                      (if write "已铺" "【只算没铺】")
                      "：箱变 " (itoa (length cabs)) " 台柜"
                      " / 槽位 " (itoa n) "（清单需 " (itoa need) "）"
                      " / 表头 2 枚（清单给了 " (itoa (length hdrs)) " 遍）" SEP
                      (if pls
                        (strcat "  分段 " (itoa nseg) "（各段独立从第 1 槽起）："
                                segtxt SEP)
                        "")
                      (if (and pls (> (length hdrs) nseg))
                        (strcat "  提示：清单只切出 " (itoa nseg)
                                " 段，清单里的表头行数与段数不一致" SEP)
                        "")
                      "  柜型定义：" cabn "，表头定义：" hdrn SEP
                      "  整排宽 " (rtos totw 2 1)
                      "（表头 " (rtos hw 2 0) " + 柜 " (itoa (length cabs))
                      "×" (rtos cw 2 0) " + 表头 " (rtos hw 2 0) "）"
                      "，框宽 " (rtos fw 2 0) SEP
                      "  落点：前表头几何左 " (rtos (+ bx *xbt:padl*) 2 1)
                      "，第 1 台柜几何左 " (rtos (+ bx *xbt:padl* hw) 2 1)
                      "，尾表头几何左 " (rtos hdrx2 2 1) SEP
                      "  清旧克隆：" (itoa cpur) " 个" SEP
                      "  行高计划：" plan
                      (if (xbt:needrows plan)
                        "  -> 已调 GGH 全排加行高"
                        "  -> 全 1 行，没调 GGH") SEP
                      "  高度：总行数 " (itoa rsum)
                      "（槽 " (itoa n) " + 加行 " (itoa (- rsum n))
                      "）× 行距 " (rtos pit 2 1)
                      " -> 块高 " (rtos bh 2 1) SEP
                      "        框高 " (rtos fh 2 0)
                      "，顶距 " (rtos *xbt:padt* 2 0)
                      "，底距 " (rtos (- fh *xbt:padt* bh) 2 1) SEP
                      (if write
                        (strcat "  实插：图框 " (itoa cntf)
                                "，表头 " (itoa cnth) "/2"
                                "，柜块 " (itoa cntc) "/" (itoa (length cabs))
                                "，占位块 " (itoa cntp) "/" (itoa (length cabs)) SEP)
                        (strcat "  只算没铺：一个字没写。" SEP))
                      (if rp (strcat "  GGH：" (car rp) SEP) "")
                      (if warns
                        (strcat "  警告 " (itoa (length warns)) " 条：" SEP
                                (apply 'strcat
                                       (mapcar '(lambda (x) (strcat "    " x SEP)) warns)))
                        "")
                      (if write "  没存盘，改动都在内存里。" "")
                    )
                  )
                  rpt
                 )
               )
              )
             )
            )
           )
          )
         )
        )
      )
    )

;; ================================================================
;; 四、入口
;; ================================================================
(defun xbt:run (tx)     (xbt:go tx T))
(defun xbt:dry (tx)     (xbt:go tx nil))
(defun xbt:runfile (f)  (xbt:go (plt:readfile f) T))
(defun xbt:dryfile (f)  (xbt:go (plt:readfile f) nil))

(defun c:XBT ( / f tx r)
  (setq f (getstring T "\n清单文件路径（ANSI/GBK 的 txt，直接回车取消）: "))
  (if (= (plt:trim f) "")
    (princ "\n取消了，什么也没做。")
    (progn
      (setq tx (plt:readfile f))
      (if (null tx)
        (princ (strcat "\n读不到这个文件：" f))
        (progn
          (setq r (xbt:go tx T))
          (princ (strcat SEP r))
        )
      )
    )
  )
  (princ)
)

(princ "\n属性块-箱变.lsp 已加载。命令 XBT（或 (xbt:run \"清单文本\")）。")
(princ)


;;; ================================================================
;;; 模块 四、属性块-铺图.lsp（PGT，命令 PGT）
;;; ================================================================

;;; ============================================================
;;; 属性块-铺图.lsp                                    命令：PGT
;;; ------------------------------------------------------------
;;; 作用
;;;   按「槽位数 + 柜号清单」铺一张一次系统图空骨架，其余数据全空：
;;;     1 每框插一份图框（图框模版.dwg）并炸开；
;;;     2 每框插一枚表头块（槽位级，全排共用一份槽位表）；
;;;     3 逐台插柜属性块，只写「柜号」，其余属性一律留空；
;;;     4 每台柜盖一枚占位块，落在系统图位置上。
;;;
;;; 两个入口
;;;   1 口述（给脚本 / 外部调用）：
;;;        (pgt:run 9 "AH01,AH02,AH03")   槽位数 + 柜号清单，真铺
;;;        (pgt:dry 9 "AH01,AH02,AH03")   同上，只算不铺
;;;     槽位数给 nil 或 0 -> 用模板自带的槽位数；
;;;     柜号既可以是 "AH01,AH02"，也可以是 ("AH01" "AH02")。
;;;   2 手动：命令 PGT —— 逐项提示，直接回车取默认。
;;;
;;; 依赖
;;;   属性块-槽位增减.lsp（gkc:* 一族；槽位数与模板不同时整排调一次）
;;;   模板 dwg（lisp 所在目录的上一级，或 CAD 支持路径能找到）：
;;;       图框模版.dwg  柜块模版.dwg  表头块模版.dwg  占位块.dwg
;;;   找不到模板就拒绝执行 —— 块定义只活在图纸自身里，
;;;   换一张图铺图必须靠模板 dwg 把定义带进来。
;;;
;;; 副作用
;;;   1 块定义要先「带进本图」才能量几何、才能插（插远处再删，图元不留）；
;;;     这一步是唯一走命令行 -INSERT 的地方（只用来把 dwg 带进来），
;;;     期间把 ATTREQ 压成 0，免得属性块索要输入；
;;;   2 槽位数与模板不同 -> 在远地造一份新定义（整排重造：句柄全变、
;;;      块名克隆成「原名-柜号/表头」），临时参照随即删掉；
;;;   3 铺进来的块定义留在这张图里（换图要重新铺一次）；
;;;   4 不存盘 —— 落不落盘你自己定。
;;;
;;; 插块为什么走 COM 而不是 (command "_.-INSERT" …)
;;;   命令行插「带属性的块」时 AutoCAD 会逐个属性索要输入（表头 32 个 /
;;;   柜块 37 个），(command …) 就永远等不到下一句 —— 实测卡死两次，
;;;   连 ESC 都注入不进去，得人工到 CAD 窗口按 ESC 才回来。
;;;   COM 的 InsertBlock 一个提示都不弹，属性按 ATTDEF 默认值带入；
;;;   server.py 主路径用的也是它（5964 / 6744 / 9041）。
;;;   炸开同样走 COM（BlockReference.Explode 不删源对象，要手动删）。
;;;
;;; 版面口径（全部从图上量出来的，不是猜的）
;;;   图框：定义里那个匿名块参照（*U3）就是框；它的几何 = 420x297，
;;;         框左下角在定义内的位置 = 锚块插入点 + 锚块几何最小角
;;;         -> 插入点要反向补偿这两项之和（锚块几何起于 0 时退化成只减插入点）
;;;   柜块：几何 x[0,35] y[-36,178]（15 槽）；槽位增减只动下半截，几何顶不变
;;;   表头块：几何 x[0,40]，与柜块同一套 y
;;;   占位块：几何 x[174.48,209.48] y[119.23,170.81]（基点离几何很远）
;;;   表头几何左 = 框左 + 35；第 1 台柜几何左 = 表头几何左 + 表头宽
;;;   柜块几何顶 = 框顶 - 14；占位块几何顶 = 柜块几何顶 - 3
;;;   第 2 框 = 第 1 框 + 框宽 + 50
;;;
;;; 编码：ANSI/GBK 无 BOM
;;; ============================================================
(vl-load-com)
(if (not (boundp 'SEP)) (setq SEP (chr 10)))

;; 表头几何左离框左 / 柜块几何顶离框顶 / 框间距 / 占位块顶离柜块顶
(setq *pgt:padl* 35.0)
(setq *pgt:padt* 14.0)
(setq *pgt:cgap* 50.0)
(setq *pgt:phgap* 3.0)

;; 造副本定义时临时摆在多远处（离正式图够远，gkc 不会认成同一排）
(setq *pgt:far* 20000.0)

;; ================================================================
;; 一、路径与依赖
;; ================================================================

(defun pgt:dir ( / f)
  (setq f (findfile "属性块-铺图.lsp"))
  (if f (vl-filename-directory f) nil)
)

;; 模板 dwg 在哪：先看 lisp 上一级，再试写死路径
(defun pgt:tpldir ( / d)
  (setq d (pgt:dir))
  (if d (setq d (vl-filename-directory d)))
  (cond
    ((and d (findfile (strcat d "/图框模版.dwg"))) d)
    ((findfile "D:/kk三部曲/148.CAD插件研究/图框模版.dwg")
     "D:/kk三部曲/148.CAD插件研究")
    (T d)
  )
)

(defun pgt:tpl (n / d f)
  (setq d (pgt:tpldir))
  (if d (setq f (findfile (strcat d "/" n))))
  (if (null f) (setq f (findfile n)))
  f
)

;; 确保 属性块-槽位增减.lsp 已加载（gkc:expand 在就算在）
(defun pgt:ensure ( / f)
  (if (not (member 'GKC:EXPAND (atoms-family 0)))
    (progn
      (setq f (findfile "属性块-槽位增减.lsp"))
      (if (null f)
        (setq f (findfile "D:/kk三部曲/148.CAD插件研究/lisp/属性块-槽位增减.lsp"))
      )
      (if f (load f))
    )
  )
  (if (member 'GKC:EXPAND (atoms-family 0)) T nil)
)

;; ================================================================
;; 二、小工具
;; ================================================================

;; 去首尾半角空格（只切 ASCII 空格，不会切坏中文）
(defun pgt:trim (s / n)
  (setq s (if s s ""))
  (while (and (> (strlen s) 0) (= 32 (ascii (substr s 1 1))))
    (setq s (substr s 2))
  )
  (setq n (strlen s))
  (while (and (> n 0) (= 32 (ascii (substr s n 1))))
    (setq s (substr s 1 (1- n)) n (1- n))
  )
  s
)

;; "AH01,AH02 AH03" -> ("AH01" "AH02" "AH03")
;; 按字节逐个走：中文柜号被切成单字节再拼回去，字节序列不变，结果正确
(defun pgt:split (s / res cur i n ch)
  (setq res nil cur "" s (pgt:trim (if s s "")) n (strlen s) i 1)
  (while (<= i n)
    (setq ch (substr s i 1))
    (if (member ch (list "," " " (chr 9) ";" (chr 10)))
      (progn (if (/= cur "") (setq res (cons cur res))) (setq cur ""))
      (setq cur (strcat cur ch))
    )
    (setq i (1+ i))
  )
  (if (/= cur "") (setq res (cons cur res)))
  (reverse res)
)

;; 向上取整 a/b（整数相除前先转实数 —— AutoLISP 的 / 对整数是整除）
(defun pgt:ceil (a b)
  (fix (/ (+ a (1- b)) (float b)))
)

;; 块定义是否存在
(defun pgt:defp (bn)
  (if (tblobjname "BLOCK" bn) T nil)
)

;; 量块定义内部几何范围 -> (minx miny maxx maxy)；块内实体坐标是相对基点的
;; 不用 COM 包围盒：LISP 侧拿到的是 safearray 不是 variant，容易炸
(defun pgt:rng (bn / e ed x q minx miny maxx maxy)
  (setq e (tblobjname "BLOCK" bn))
  (if (null e)
    nil
    (progn
      (setq e (entnext e) minx 1e9 miny 1e9 maxx -1e9 maxy -1e9)
      (while (and e (/= "ENDBLK" (cdr (assoc 0 (entget e)))))
        (setq ed (entget e))
        (foreach x ed
          (setq q (cdr x))
          (if (and (member (car x) (list 10 11)) (listp q))
            (progn
              (if (< (car q) minx) (setq minx (car q)))
              (if (< (cadr q) miny) (setq miny (cadr q)))
              (if (> (car q) maxx) (setq maxx (car q)))
              (if (> (cadr q) maxy) (setq maxy (cadr q)))
            )
          )
        )
        (setq e (entnext e))
      )
      (list minx miny maxx maxy)
    )
  )
)

;; 图框模版定义里的「锚块」：那个匿名块参照（名以 * 开头），
;; 它的位置就是框左下角相对基点的偏移。返回 (块名 锚点x 锚点y)
(defun pgt:fanchor ( / e ed bn p r)
  (setq e (tblobjname "BLOCK" "图框模版") r nil)
  (if e
    (progn
      (setq e (entnext e))
      (while (and e (/= "ENDBLK" (cdr (assoc 0 (entget e)))))
        (setq ed (entget e))
        (if (= "INSERT" (cdr (assoc 0 ed)))
          (progn
            (setq bn (cdr (assoc 2 ed)) p (cdr (assoc 10 ed)))
            (if (and bn p (= "*" (substr bn 1 1)))
              (setq r (list bn (car p) (cadr p)))
            )
          )
        )
        (setq e (entnext e))
      )
    )
  )
  r
)

;; 取 GKC 回包里 "|标记值|" 的那一段（标记是 ASCII）
;; 注意：一律用 gkc:bfind 定位 —— 它按字节回 1 基下标，配 substr 不会错位
(defun pgt:kv (s key / p q)
  (setq p (gkc:bfind s key))
  (if p
    (progn
      (setq p (+ p (strlen key)))
      (setq q (gkc:bfind (substr s p) "|"))
      (substr s p (if q (1- q) 9999))
    )
    nil
  )
)

;; 从 "@defs=旧>新;旧>新;" 里找指定旧名对应的新名
(defun pgt:newdef (s obn / r p q seg)
  (setq r nil s (if s s ""))
  (while (setq p (gkc:bfind s ";"))
    (setq seg (substr s 1 (1- p)) s (substr s (1+ p)))
    (setq q (gkc:bfind seg ">"))
    (if (and q (= obn (substr seg 1 (1- q))))
      (setq r (substr seg (1+ q)))
    )
  )
  (if (> (strlen s) 0)
    (progn
      (setq q (gkc:bfind s ">"))
      (if (and q (= obn (substr s 1 (1- q))))
        (setq r (substr s (1+ q)))
      )
    )
  )
  r
)

;; 删掉 *pgt:far* 附近的块参照（±500）—— 造副本定义留下的临时件
;; 注意：用「区间」而不是「大于」：正式图起点万一摆得很大，按 > 判会误删
(defun pgt:purgef (c / ss n i e ed p cnt lo hi)
  (setq ss (ssget "_X" '((0 . "INSERT") (410 . "Model")))
        n (if ss (sslength ss) 0) i 0 cnt 0
        lo (- c 500.0) hi (+ c 500.0))
  (while (< i n)
    (setq e (ssname ss i) ed (entget e) p (cdr (assoc 10 ed)))
    (if (and p (> (car p) lo) (< (car p) hi))
      (progn (entdel e) (setq cnt (1+ cnt)))
    )
    (setq i (1+ i))
  )
  cnt
)

;; ================================================================
;; 三、插块（全走 COM）
;; ================================================================
;; 为什么不用 (command "_.-INSERT" …) 插正式块：见文件头。COM 不问任何东西。
;; 变体 / 安全数组 -> 普通表（COM 在 LISP 侧两种都可能吐出来）
(defun pgt:aslist (r / v)
  (cond
    ((= (type r) 'safearray)
     (setq v (vl-catch-all-apply 'vlax-safearray->list (list r)))
     (if (vl-catch-all-error-p v) nil v))
    ((= (type r) 'variant)
     (setq v (vl-catch-all-apply 'vlax-variant-value (list r)))
     (if (vl-catch-all-error-p v)
       nil
       (if (= (type v) 'safearray)
         (progn
           (setq v (vl-catch-all-apply 'vlax-safearray->list (list v)))
           (if (vl-catch-all-error-p v) nil v))
         nil)))
    ((listp r) r)
    (T nil)
  )
)

;; 当前文档的模型空间（COM），拿不到返回 nil
(defun pgt:ms ( / app d)
  (setq app (vl-catch-all-apply 'vlax-get-acad-object nil))
  (if (vl-catch-all-error-p app)
    nil
    (progn
      (setq d (vl-catch-all-apply 'vla-get-ActiveDocument (list app)))
      (if (vl-catch-all-error-p d)
        nil
        (progn
          (setq d (vl-catch-all-apply 'vla-get-ModelSpace (list d)))
          (if (vl-catch-all-error-p d) nil d)
        )
      )
    )
  )
)

;; 插一个块参照（按块名，块定义必须已在本图）-> VLA 对象；失败 nil
;; 先按 6 参（x y z 比例 + 转角），不行再退 5 参（x y 比例 + 转角）——
;;   不同版本的 InsertBlock 签名不一样，两条都试一次比赌一条稳
(defun pgt:ins (bn pt / ms p r)
  (setq ms (pgt:ms))
  (if (null ms)
    nil
    (progn
      (setq p (vlax-3d-point (car pt) (cadr pt) 0.0))
      ;; 必须走直连包装 vla-InsertBlock，6 参：插入点 + 块名 + x y z 比例 + 转角
      ;;   vlax-invoke 那条路在本机不通（实测 2026-09-20）：
      ;;     6 参回「发生意外。」，5 参回「无效的参数数目。」
      ;;     —— 和当初 vlax-invoke 'Move 报「发生意外」是同一类毛病
      ;;   插入点也必须用 vlax-3d-point：传普通表会回
      ;;     「此类型的 LISP 值不能强制转换成 VARIANT」
      (setq r (vl-catch-all-apply 'vla-InsertBlock
                (list ms p bn 1.0 1.0 1.0 0.0)))
      (if (vl-catch-all-error-p r) (setq r nil))
      r
    )
  )
)

;; 命令行 -INSERT，只用来把「模板 dwg 文件」带进本图（按路径插，插完就删）
;;   COM 的 InsertBlock 不吃文件路径（server.py 8693 记过这条），所以这里
;;   是全文唯一保留命令行插块的地方 —— 这条路实测是通的（临时件不带属性值）。
(defun pgt:insf (path pt / before e oa)
  (setq before (entlast))
  (setq oa (getvar "ATTREQ"))
  (setvar "ATTREQ" 0)
  (command "_.-INSERT" (strcat "\"" path "\"") pt 1 1 0)
  (setvar "ATTREQ" oa)
  (setq e (entlast))
  (if (equal e before) nil e)
)

;; 炸开一层（COM）+ 删源对象：COM 的 Explode 不像 EXPLODE 命令那样删源
(defun pgt:exp (ref / r)
  (if ref
    (progn
      (setq r (vl-catch-all-apply 'vla-Explode (list ref)))
      (if (vl-catch-all-error-p r) (setq r nil))
      (vl-catch-all-apply 'vla-Delete (list ref))
      (pgt:aslist r)
    )
  )
)

;; 写属性值（按标签精确定位，只改这一个）
(defun pgt:setatt (ref tg val / lst a tgv)
  (if ref
    (progn
      (setq lst (pgt:aslist (vl-catch-all-apply 'vla-GetAttributes
                               (list ref))))
      (foreach a lst
        (if (= (type a) 'VLA-OBJECT)
          (progn
            (setq tgv (vl-catch-all-apply 'vla-get-TagString (list a)))
            (if (and (not (vl-catch-all-error-p tgv)) (= tg tgv))
              (vl-catch-all-apply 'vla-put-TextString (list a val))
            )
          )
        )
      )
    )
  )
  val
)

;; 把模板 dwg 的块定义带进本图（已经有就不动它）；成了返回 T
(defun pgt:import (dwg bn / f e)
  (if (pgt:defp bn)
    T
    (progn
      (setq f (pgt:tpl dwg))
      (if (null f)
        nil
        (progn
          (setq e (pgt:insf f (list *pgt:far* 0.0)))
          (if e (entdel e))
          (pgt:defp bn)
        )
      )
    )
  )
)

;; ================================================================
;; 四、定槽：拿到「槽数 = n」的柜块 / 表头块定义名
;; ================================================================
;; 模板是固定槽数的。用户要别的槽数时，在远地插一对（1 表头 + 1 柜），
;; 调一次 gkc:expand 让整排变成 n 槽，记下新定义名，再把临时参照删掉。
;; 这样「调槽」整张图只发生一次，正式铺图直接用现成的定义。
;; 返回 (柜块名 表头块名 实际槽数)
;; 注意：临时件摆成「相邻」（表头在 20000、柜块在 20040，表头宽正好 40），
;;   gkc:rowfill 才会按几何把它们判成同一排，一起 ±k；分开摆会只变一半。
(defun pgt:defs (n cab0 hdr0 / cur r e1 e2 h1 h2 nc nh)
  (setq cur (gkc:maxslot cab0))
  (if (or (null n) (<= n 0) (null cur) (= cur n))
    (list cab0 hdr0 cur)
    (progn
      (setq e1 (pgt:ins hdr0 (list *pgt:far* 0.0)))
      (setq e2 (pgt:ins cab0 (list (+ *pgt:far* 40.0) 0.0)))
      (if (or (null e1) (null e2))
        (list cab0 hdr0 cur)
        (progn
          (setq h1 (vl-catch-all-apply 'vla-get-Handle (list e1)))
          (setq h2 (vl-catch-all-apply 'vla-get-Handle (list e2)))
          (if (or (vl-catch-all-error-p h1) (vl-catch-all-error-p h2))
            (progn (pgt:purgef *pgt:far*) (list cab0 hdr0 cur))
            (progn
              (setq r (gkc:expand (strcat h1 "," h2) (- n cur)))
              (setq nc (pgt:newdef (pgt:kv r "@defs=") cab0))
              (setq nh (pgt:newdef (pgt:kv r "@defs=") hdr0))
              (pgt:purgef *pgt:far*)
              (if (and nc nh)
                (list nc nh n)
                (list cab0 hdr0 cur)
              )
            )
          )
        )
      )
    )
  )
)

;; 清掉上轮未引用的克隆定义（柜块模版-排* / 表头块模版-表头*），腾干净名字。
;; 被引用的 -PURGE 会自己拒绝。返回清掉几个。与 xbt:purgeold 同口径。
(defun pgt:purgeold ( / b nm lst k ce)
  (setq b (tblnext "BLOCK" T) lst nil)
  (while b
    (setq nm (cdr (assoc 2 b)))
    (if (and (/= nm "") (wcmatch nm "柜块模版-排*,表头块模版-表头*"))
      (setq lst (cons nm lst))
    )
    (setq b (tblnext "BLOCK"))
  )
  (setq k 0 ce (getvar "CMDECHO"))
  (setvar "CMDECHO" 0)
  (foreach nm lst
    (if (tblobjname "BLOCK" nm)
      (progn
        (command "_.-PURGE" "_B" nm "_N")
        (if (null (tblobjname "BLOCK" nm)) (setq k (1+ k)))
      )
    )
  )
  (setvar "CMDECHO" ce)
  k
)

;; ================================================================
;; 五、主流程
;; ================================================================
;; slots = 槽位数（nil/0 = 用模板的）   cabs = 柜号表
;; per   = 每框台数（nil = 按框宽自动）  bx by = 第 1 框左下角
;; write = T 真铺 / nil 只算不铺
(defun pgt:go (slots cabs per bx by write / ok msg dfs cabn hdrn n
               fa ar fr cr hr pr fw fh step hw cw
               crx cry hrx hry phx phy
               m k nfr fi fi2 j idx left cno e tpl tot
               fok hok cok pok cpur
               ftop cabx caby hdrx hdry phxx phyy cabht)
  (cond
    ((null (pgt:ensure))
     "缺 属性块-槽位增减.lsp（找不到或加载失败），没动图。")
    ((null cabs)
     "柜号清单是空的，没动图。")
    (T
     ;; --- 模板文件齐不齐 ---
     (setq msg "")
     (foreach tpl (list "图框模版.dwg" "柜块模版.dwg" "表头块模版.dwg" "占位块.dwg")
       (if (null (pgt:tpl tpl)) (setq msg (strcat msg "  缺模板：" tpl SEP)))
     )
     (cond
       ((/= msg "")
        (strcat "模板不齐，没动图：" SEP msg
                "  模板目录：" (if (pgt:tpldir) (pgt:tpldir) "?")))
       ((and write (null (pgt:ms)))
        "拿不到模型空间（COM 没通），没动图。")
       (T
        ;; --- 把四个块定义带进本图（只加定义，不加图元）---
        (pgt:import "图框模版.dwg" "图框模版")
        (pgt:import "柜块模版.dwg" "柜块模版")
        (pgt:import "表头块模版.dwg" "表头块模版")
        (pgt:import "占位块.dwg" "占位块")
        (cond
          ((or (null (pgt:defp "图框模版")) (null (pgt:defp "柜块模版"))
               (null (pgt:defp "表头块模版")) (null (pgt:defp "占位块")))
           "四个块定义没全进到本图（模板插不进来？），没动图。")
          (T
           (setq cpur (pgt:purgeold))
           ;; --- 定槽 ---
           (setq dfs (pgt:defs slots "柜块模版" "表头块模版"))
           (setq cabn (car dfs) hdrn (cadr dfs) n (caddr dfs))
           ;; --- 量几何 ---
           (setq fa (pgt:fanchor))
           (setq ar (if fa (pgt:rng (car fa))))
           (setq cr (pgt:rng cabn)
                 hr (pgt:rng hdrn)
                 pr (pgt:rng "占位块"))
           (cond
             ((null fa)
              "图框模版里找不到锚块（那个 * 开头的匿名块参照），没动图。")
             ((or (null ar) (null cr) (null hr) (null pr))
              "量不到块定义几何（图框 / 柜块 / 表头 / 占位块 有一个缺），没动图。")
             (T
              (setq fw (- (nth 2 ar) (car ar)))        ; 框宽 420
              (setq fh (- (nth 3 ar) (nth 1 ar)))      ; 框高 297
              (setq step (+ fw *pgt:cgap*))            ; 框间距 470
              (setq hw (- (nth 2 hr) (car hr)))        ; 表头块宽 40
              (setq cw (- (nth 2 cr) (car cr)))        ; 柜块宽 35
              (setq crx (car cr) cry (nth 3 cr))       ; 柜块几何 左 / 顶
              (setq hrx (car hr) hry (nth 3 hr))       ; 表头几何 左 / 顶
              (setq phx (car pr) phy (nth 3 pr))       ; 占位块几何 左 / 顶
              (setq cabht (- cry (nth 1 cr)))          ; 柜块几何高
              ;; 每框几台：框内净宽 / 柜宽
              (setq k (if (and per (> per 0)) per
                        (fix (/ (- fw (+ *pgt:padl* hw)) (float cw)))))
              (if (< k 1) (setq k 1))
              (setq m (length cabs))
              (setq nfr (pgt:ceil m k))
              ;; 与第几台无关的那几个 y / 偏移，循环外算一次
              (setq ftop (+ by fh))                          ; 框顶
              (setq caby (- ftop *pgt:padt* cry))            ; 柜块插入点 y
              (setq hdry (- ftop *pgt:padt* hry))            ; 表头插入点 y
              (setq phyy (- ftop *pgt:padt* *pgt:phgap* phy)) ; 占位块插入点 y
              ;; --- 逐框铺 ---
              (setq tot 0 fi 0 fok 0 hok 0 cok 0 pok 0)
              (while (< fi nfr)
                (setq left (+ bx (* fi step)))               ; 本框左下角 x
                (if write
                  (progn
                    ;; 图框：COM 插 + COM 炸开（框左下角在定义内要反向补偿）
                    (setq e (pgt:ins "图框模版"
                                     (list (- left (cadr fa) (car ar))
                                           (- by (caddr fa) (nth 1 ar)))))
                    (if e (progn (setq fok (1+ fok)) (pgt:exp e)))
                    ;; 本框表头，只一枚
                    (if (pgt:ins hdrn (list (- (+ left *pgt:padl*) hrx) hdry))
                      (setq hok (1+ hok))
                    )
                  )
                )
                ;; 本框的柜 + 占位块
                (setq j 0)
                (while (and (< j k) (< (+ (* fi k) j) m))
                  (setq idx (+ (* fi k) j))
                  (setq cno (nth idx cabs))
                  (setq cabx (+ left *pgt:padl* hw (* j cw)))   ; 本台柜几何左
                  (if write
                    (progn
                      (setq e (pgt:ins cabn (list (- cabx crx) caby)))
                      (if e (progn (setq cok (1+ cok)) (pgt:setatt e "柜号" cno)))
                      (if (pgt:ins "占位块" (list (- cabx phx) phyy))
                        (setq pok (1+ pok))
                      )
                    )
                  )
                  (setq tot (1+ tot))
                  (setq j (1+ j))
                )
                (setq fi (1+ fi))
              )
              ;; --- 报告 ---
              (strcat
                (if write "已铺" "【只算没铺】")
                "：槽位 " (itoa n)
                "（" (if (= cabn "柜块模版") "用模板定义" "现场克隆了新定义") "，柜块几何高 "
                (rtos cabht 2 0) "）" SEP
                "  柜 " (itoa m) " 台 / 每框 " (itoa k) " 台 / 共 " (itoa nfr) " 框" SEP
                (if write
                  (strcat "  实插：图框 " (itoa fok) "/" (itoa nfr)
                          "，表头 " (itoa hok) "/" (itoa nfr)
                          "，柜块 " (itoa cok) "/" (itoa tot)
                          "，占位块 " (itoa pok) "/" (itoa tot) SEP)
                  (strcat "  只算没铺：一个字没写。" SEP))
                "  清未引用克隆 " (itoa (if cpur cpur 0)) " 个" SEP
                "  框 " (rtos fw 2 0) "x" (rtos fh 2 0)
                "，间距 " (rtos step 2 0)
                "；柜块插入点 y = " (rtos caby 2 1)
                "，第 1 台柜几何左 = " (rtos (+ bx *pgt:padl* hw) 2 1) SEP
                (if write "  没存盘，改动都在内存里。" "")
              )
             )
           )
          )
        )
       )
     )
    )
  )
)

;; ================================================================
;; 六、入口
;; ================================================================

;; 柜号可以给字符串（"AH01,AH02"）也可以直接给表（("AH01" "AH02")）
(defun pgt:cl (c)
  (if (listp c) c (pgt:split c))
)

;; 每框台数要走指定值时，直接调 (pgt:go 槽数 柜号表 每框台数 bx by write)
(defun pgt:run (slots cabs)
  (pgt:go slots (pgt:cl cabs) nil 0.0 0.0 T)
)

(defun pgt:dry (slots cabs)
  (pgt:go slots (pgt:cl cabs) nil 0.0 0.0 nil)
)

(defun c:PGT ( / s per cabs r)
  (setq s (getint "\n槽位数 <用模板自带的>: "))
  (setq per (getint "\n每框台数 <按框宽自动>: "))
  (setq cabs (getstring T "\n柜号清单（逗号或空格分隔，如 AH01,AH02）: "))
  (setq r (pgt:go s (pgt:split cabs) per 0.0 0.0 T))
  (princ (strcat SEP r))
  (princ)
)

(princ "\n属性块-铺图.lsp 已加载。命令 PGT（或 (pgt:run 9 \"AH01,AH02\")）。")
(princ)


;;; ================================================================
;;; 模块 五、属性块-批量填数.lsp（PLT，命令 PLT）
;;; ================================================================

;;; ============================================================
;;; 属性块-批量填数.lsp                                命令：PLT
;;; ------------------------------------------------------------
;;; 作用
;;;   在 PGT 铺好的空壳上，按一份清单把数据灌进去 —— 只写字，
;;;   不动任何几何、不建块、不插块、不扩容。
;;;     · 柜块：柜用途 / 柜型 / 柜尺寸 / 容量功率 / 分支电流 / 备注
;;;     · 柜块槽位：元件NN规格 / 元件NN数量
;;;     · 表头块：主母线规格 / 电压等级
;;;     · 表头块槽位：元件NN名称 / 元件NN型号
;;;     · 图签 7 格：柜型 / 图名 / 数量 / 工程号 / 图号 / 共X张 / 第X张
;;;       （模型空间的独立 TEXT，不是块属性）
;;;   没数据的槽一律写空 —— 重复跑幂等，不会留残留旧值。
;;;
;;; 清单格式（与 acad-mcp 的 compact 口同源）
;;;     表头 | 3*80*6 | 10kV                        <- 可选，可写多遍：
;;;                                                   第 j 遍对应图上从左到右
;;;                                                   第 j 枚表头（箱变两段）
;;;     图签 | GGD | 进线 D1 | JX01 | QC | *         <- 可选
;;;     @AH01 | 进线柜 | KYN28A-12 | 800*1500*2300 | 630KVA | | 下进上出
;;;     1 | 真空断路器 | VS1-12 | 630A 25kA | 1
;;;     5 | 电压互感器 | JDZ10-10 | 10/0.1kV | 3
;;;     @AH02 | ...
;;;   规则：
;;;     · 柜头行必须 @ 开头：柜号 | 柜用途 | 柜型 | 柜尺寸 | 容量功率 |
;;;       分支电流 | 备注（后 6 段可省，空段有意义）
;;;     · 元件行：槽号 | 名称 | 型号 | 规格 | 数量；槽号可写 - 或整段省略
;;;     · 字段分隔用 | 或 tab（**连续空格不拆**，规格里本来就有空格）
;;;     · 图签行：柜型 | 图名 | 图号 | 工程号前缀 | 日期（后 2 段可省）
;;;         - 工程号：日期段空 -> 前缀原样；`*` -> 前缀 + 当天 YYYYMMDD；
;;;           给了别的就照拼
;;;         - 数量 / 共X张 / 第X张 三格自动算，不用写
;;;         - 整行不写 -> 那 4 格**写空**（清掉图框模版预置值；
;;;           与 acad-mcp 的 frame_finish 同口径，2026-09-20 改）
;;;     · 空行 / # / // 开头的行跳过
;;;
;;; 入口
;;;   (plt:run "清单文本")           真写（含图签）
;;;   (plt:dry "清单文本")           只算不写（报槽数 + 逐槽分配 + 警告）
;;;   (plt:need "清单文本")          只报需要几个槽
;;;   (plt:runfile "清单.txt") / (plt:dryfile ...)   从 GBK 文件读
;;;   (plt:titlerun "柜型|图名|图号|工程号前缀|日期")  只重填图签
;;;      只填图签的专用入口见 → 属性块-填图签.lsp（命令 TQ，带逐格明细）
;;;   命令 PLT —— 交互，问清单文件路径
;;;
;;; 为什么不能拿 JYJ 循环喂
;;;   JYJ 的槽位是「占表头第一个空槽」→ 槽号依赖喂入顺序；本工具是
;;;   「显式槽号优先，没给的按首次出现顺序取最小空槽」→ 与 MCP 的
;;;   att_panel(compact=) 同口径：同名同型号在所有柜落**同一槽**。
;;;
;;; 已知边界
;;;   1 不扩容：清单需要的槽数 > 图上槽数 → 直接拒绝并报数字，
;;;     请先用 PGT / XBT 按需要的槽数铺图。
;;;   2 【2026-09-20 起】行高、多表头都已支持：
;;;     · 多行规格：槽位若已被 XBT 加过行高（标签是 元件NN规格1..M），
;;;       本工具按同一套宽度规则拆行分别落位；单行标签（元件NN规格）
;;;       照旧只写一行、超宽仍只报 warning。
;;;     · 多表头：清单里「表头」行可以写多遍，第 j 遍对应图上从左到右
;;;       第 j 枚表头（箱变两段：第 1 遍高压、第 2 遍低压）。只写一遍时
;;;       发给所有表头（旧行为，KYN28 单段不受影响）。
;;;     · 表头参照按插入点 x 从左到右排序后逐枚对应（不再按图元生成序）。
;;;     · 本柜某槽只填了 kk 行（< 该槽格数 m）时，这 kk 行【整组】挪到槽的
;;;       垂直中心（锚点 = 该槽「数量」属性的 y；位移按相对给，见 plt:midrow）。
;;;
;;; 依赖
;;;   无（自包含）。只认「图上已经铺好的块」。
;;;
;;; 写值走 entmod 改组码 1，不走 COM —— CWJH 已验证这条路稳；
;;; 本机 vlax-invoke 调 COM 方法不通（要走 vla- 直连），能不碰就不碰。
;;;
;;; 注意：substr / strlen 在 DBCS 下按**字节**计数（中文占 2 字节），
;;;   所以下面凡是切中文前缀一律用字节下标，且按 ASCII 单字节分隔符
;;;   逐字节拆 —— 不能拿 vl-string-search 的下标去 substr（单位不同）。
;;;
;;; 编码：ANSI/GBK 无 BOM
;;; ============================================================
(vl-load-com)
(if (not (boundp 'SEP)) (setq SEP (chr 10)))

;; ------------------------------------------------------------
;; 常量
;; ------------------------------------------------------------
(setq *plt:prefix*   "元件")        ; 槽位标签前缀
(setq *plt:tag-cab*  "柜号")        ; 认柜块参照的标签
(setq *plt:tag-hdr*  "主母线规格")  ; 认表头块参照的标签
 (setq *plt:slot-col* 9.0)           ; 规格栏可容宽度（em）= 27 列宽 / 3.0 字高
(setq *plt:em-ascii* 0.5)           ; 西文平均字宽（em）
;; 图签（模型空间独立 TEXT）—— 实测口径见「四·五」节
(setq *plt:frame-w* 420.0)          ; 单套图框宽（A3 横 420）
(setq *plt:tb-cells* '(
  ("product" -100.0 -50.0 18.5 28.0)
  ("title"   -100.0 -50.0  9.0 18.5)
  ("qty"      -50.0   0.0 18.5 28.0)
  ("project"  -50.0   0.0  9.0 18.5)
  ("code"     -50.0   0.0  0.0  9.0)
  ("total"   -100.0 -75.0  0.0  9.0)
  ("no"       -75.0 -50.0  0.0  9.0)))

;; ================================================================
;; 一、小工具（全部按字节走，DBCS 安全）
;; ================================================================

;; 去首尾半角空白（空格 / tab / 回车）—— 只切 ASCII，不会切坏中文
(defun plt:trim (s / n)
  (setq s (if s s ""))
  (while (and (> (strlen s) 0) (member (ascii (substr s 1 1)) '(32 9 13)))
    (setq s (substr s 2))
  )
  (setq n (strlen s))
  (while (and (> n 0) (member (ascii (substr s n 1)) '(32 9 13)))
    (setq s (substr s 1 (1- n)) n (1- n))
  )
  s
)

;; 按单字节分隔符拆（逐字节走；中文被切成单字节再拼回去，字节序列不变）
(defun plt:bcut (s d / res cur i n ch)
  (setq res nil cur "" i 1 n (strlen s))
  (while (<= i n)
    (setq ch (substr s i 1))
    (if (= d (ascii ch))
      (setq res (cons cur res) cur "")
      (setq cur (strcat cur ch))
    )
    (setq i (1+ i))
  )
  (reverse (cons cur res))
)

;; s 是否以 p 开头（LISP 字符串比较就是字节序列比较）
(defun plt:pfx (s p / n)
  (setq n (strlen p))
  (and (>= (strlen s) n) (= p (substr s 1 n)))
)

;; 纯 ASCII 数字串
(defun plt:num (s / i n c ok)
  (setq s (if s s ""))
  (setq i 1 n (strlen s) ok (if (> n 0) T nil))
  (while (<= i n)
    (setq c (ascii (substr s i 1)))
    (if (or (< c 48) (> c 57)) (setq ok nil))
    (setq i (1+ i))
  )
  ok
)

;; 全角竖线 -> 半角（可能多个，循环替换）
(defun plt:normbar (s / k)
  (setq k 0)
  (while (and (< k 20) (vl-string-search "｜" s))
    (setq s (vl-string-subst "|" "｜" s) k (1+ k))
  )
  s
)

;; 去首部分隔符与空白（含全角 ｜ ：——GBK 双字节标点首字节 163，跳 2 字节）
(defun plt:lstrip (s / go c)
  (setq go T)
  (while (and go (> (strlen s) 0))
    (setq c (ascii (substr s 1 1)))
    (cond
      ((member c '(32 9 13 124 58)) (setq s (substr s 2)))
      ((= c 163) (setq s (substr s 3)))
      (T (setq go nil))
    )
  )
  s
)

;; 一行 -> 字段表：tab 优先（连续 tab 剔空段），其次 | ，都没有则整行一段
(defun plt:fields (ln / s out)
  (setq s (plt:normbar (if ln ln "")))
  (cond
    ((vl-string-search "\t" s)
     (setq out (vl-remove "" (plt:bcut s 9)))
    )
    ((vl-string-search "|" s)
     (setq out (plt:bcut s 124))
    )
    (T (setq out (list s)))
  )
  (mapcar 'plt:trim out)
)

;; 文本 -> 行表（按 LF 拆；CR 由 trim 收掉）
(defun plt:lines (tx)
  (mapcar 'plt:trim (plt:bcut (if tx tx "") 10))
)

;; 读 GBK 文本文件 -> 字符串（每行补 LF）；打不开返回 nil
(defun plt:readfile (f / h ln out)
  (setq h (open f "r"))
  (if (null h)
    nil
    (progn
      (setq out "")
      (while (setq ln (read-line h))
        (setq out (strcat out ln "\n"))
      )
      (close h)
      out
    )
  )
)

;; s 以标签 p 开头、且 p 之后紧跟分隔符或行尾 -> T
;;   （「电压互感器」也以「电压」开头 —— 不加这一条会被吃成信息区）
(defun plt:hit (s p / n r c)
  (setq n (strlen p))
  (if (and (>= (strlen s) n) (= p (substr s 1 n)))
    (progn
      (setq r (substr s (1+ n)))
      (if (= r "")
        T
        (progn
          (setq c (ascii (substr r 1 1)))
          (if (member c '(32 9 124 58 163)) T nil)
        )
      )
    )
    nil
  )
)

;; 补/截到 n 个元素（不足补 ""）
(defun plt:pad (lst n / out i)
  (setq out nil i 0)
  (while (and lst (< i n))
    (setq out (cons (car lst) out) lst (cdr lst) i (1+ i))
  )
  (setq out (reverse out))
  (while (< i n)
    (setq out (append out (list "")) i (1+ i))
  )
  out
)

;; nil -> ""
(defun plt:s1 (x)
  (if x x "")
)

;; 连续整数表 (a a+1 ... b)
(defun plt:seq (a b / out)
  (setq out nil)
  (while (>= b a)
    (setq out (cons b out) b (1- b))
  )
  out
)

;; 槽号 k -> 槽位标签（1..9 补零成 01..09）
(defun plt:tagk (k suf)
  (strcat *plt:prefix* (if (< k 10) (strcat "0" (itoa k)) (itoa k)) suf)
)

;; 估算字符串显示宽度（em）：ASCII 0.5、中文（GBK 双字节）1.0
(defun plt:em (s / i n w c)
  (setq s (if s s ""))
  (setq i 1 n (strlen s) w 0.0)
  (while (<= i n)
    (setq c (ascii (substr s i 1)))
    (if (< c 128)
      (setq w (+ w *plt:em-ascii*) i (1+ i))
      (setq w (+ w 1.0) i (+ i 2))
    )
  )
  w
)

;; ================================================================
;; 二、解清单
;; ================================================================

;; 注释行正文：剥掉行首的 # / // 前缀与空白（槽位顺序块用）
(defun plt:cmt (ln / s)
  (setq s (plt:trim ln))
  (while (or (plt:pfx s "#") (plt:pfx s "//"))
    (setq s (plt:trim (substr s 2)))
  )
  s
)

;; 清单末尾「# 槽位顺序（…）」注释块 -> ((段号 (槽号 . 名称) …) …)
;;   · 块头：注释行正文以「槽位顺序」开头 —— 一个块 = 一段，段号按块
;;     出现顺序从 1 起，与「表头行切段」切出来的段号一一对应
;;     （网页生成器写回时先高压后低压，与图上表头从左到右同序）
;;   · 块体：注释行正文形如「序号|名称」（| / tab 分隔都认）
;;   · 槽号【按块内行序重编 1,2,3…】，不信行首那个序号 ——
;;     生成器的序号在箱变低压段是接着高压段续号的（4、5…），
;;     而本程序两段各自从第 1 槽起，按行序重编才与段号口径对齐
(defun plt:sdefs (tx / out cur on ln b fs n)
  (setq out nil cur nil on nil)
  (foreach ln (plt:lines tx)
    (if (member (substr (plt:trim ln) 1 1) '("#" "/"))
      (progn
        (setq b (plt:cmt ln))
        (cond
          ((plt:pfx b "槽位顺序")
           (if on (setq out (cons (reverse cur) out)))
           (setq cur nil on T)
          )
          (on
           (setq fs (plt:fields b))
           (if (and (cadr fs) (/= (cadr fs) ""))
             (setq cur (cons (cons (1+ (length cur)) (cadr fs)) cur))
           )
          )
        )
      )
      (if on (progn (setq out (cons (reverse cur) out)) (setq cur nil on nil)))
    )
  )
  (if on (setq out (cons (reverse cur) out)))
  (setq out (reverse out) n 0)
  (mapcar '(lambda (x) (setq n (1+ n)) (cons n x)) out)
)

;; 取第 sg 段的槽位顺序定义（没这一块 -> nil = 退回首次出现顺序）
(defun plt:sdef-at (sdefs sg / r x)
  (setq r nil)
  (foreach x sdefs
    (if (and (null r) (= (car x) sg)) (setq r (cdr x)))
  )
  r
)

;; 清单文本 -> (母线 电压 柜表 警告表 图签 表头段 槽位顺序段)
;;   柜表 = ((柜号 柜用途 柜型 柜尺寸 容量功率 分支电流 备注 元件表) ...)
;;   元件表 = ((槽号 名称 型号 规格 数量 行号) ...)   槽号 nil = 没给
;;   槽位顺序段 = ((段号 (槽号 . 名称) …) …)   清单没写这块就是 nil
(defun plt:parse (tx / bus vol cabs cur comps warns n s fs e slot tb hdrs hb hv
                     seg cseg sd)
  (setq bus "" vol "" cabs nil cur nil comps nil warns nil n 0 tb nil hdrs nil
        seg 0 cseg 1)
  (foreach s (plt:lines tx)
    (setq n (1+ n))
    (cond
      ;; 空行 / 注释
      ;;   （# 行整行跳过；末尾那段「# 槽位顺序」块由 plt:sdefs 单独
      ;;     解析成排槽定义，不在这里当数据行处理）
      ((= s "") nil)
      ((plt:pfx s "#") nil)
      ((plt:pfx s "//") nil)
      ;; 图签行（必须在柜头行/元件行之前判 —— 它不以 @ 开头）
      ((plt:hit s "图签")
       (setq fs (plt:fields (plt:lstrip (substr s 5))))
       (setq tb (plt:pad fs 5))
      )
      ;; 信息区（表头 / 母线 / 母排 / 电压等级 / 电压）
      ;;   表头行可写多遍：第 j 遍对应图上【从左到右第 j 枚】表头 ——
      ;;   箱变两段就是「第 1 遍高压、第 2 遍低压」。只写一遍时发给所有表头
      ;;   （旧行为，KYN28 单段不受影响）。
      ((plt:hit s "表头")
       (setq fs (plt:fields (plt:lstrip (substr s 5))))
       (setq hb (if (and fs (car fs) (/= (car fs) "")) (car fs) ""))
       (setq hv (if (and fs (cadr fs)) (cadr fs) ""))
       (setq hdrs (cons (list hb hv) hdrs))
       (if (= (length hdrs) 1) (setq bus hb vol hv))
       ;; 【段号自增】一条表头行 = 开始新的一段 —— 其后出现的柜都属这一段
       ;;   只写 1 条表头行 -> 全图 1 段（KYN28 老路，行为不变）
       (setq seg (1+ seg))
      )
      ((plt:hit s "母线") (setq bus (plt:lstrip (substr s 5))))
      ((plt:hit s "母排") (setq bus (plt:lstrip (substr s 5))))
      ((plt:hit s "电压等级") (setq vol (plt:lstrip (substr s 9))))
      ((plt:hit s "电压") (setq vol (plt:lstrip (substr s 5))))
      ;; 柜头行
      ((plt:pfx s "@")
       (if cur (setq cabs (cons (append cur (list (reverse comps)) (list cseg)) cabs)))
       (setq cur nil comps nil)
       (setq fs (plt:fields (substr s 2)))
       (if (or (null fs) (null (car fs)) (= (car fs) ""))
         (setq warns (cons (strcat "第 " (itoa n) " 行柜头行没写柜号 —— 跳过") warns))
         (progn
           (setq cur (cons (car fs) (plt:pad (cdr fs) 6)))
           ;; 段号【当场快照】—— 不能等收尾再读 seg，
           ;;   段号会在柜头行之间（下一条表头行处）变
           (setq cseg (if (< seg 1) 1 seg))
         )
       )
      )
      ;; 元件行
      (T
       (if (null cur)
         (setq warns (cons (strcat "第 " (itoa n) " 行前面还没有柜头行 —— 跳过"
                                   "（柜头行必须以 @ 开头）") warns))
         (progn
           (setq fs (plt:fields s) slot nil)
           (if (and fs (plt:num (car fs)))
             (setq slot (atoi (car fs)) fs (cdr fs))
             (if (member (car fs) '("-" "_" "—"))
               (setq fs (cdr fs))
             )
           )
           (if (or (null fs) (null (car fs)) (= (car fs) ""))
             (setq warns (cons (strcat "第 " (itoa n) " 行元件行没写名称 —— 跳过") warns))
             (progn
               (setq e (list slot
                             (car fs)
                             (plt:s1 (cadr fs))
                             (plt:s1 (caddr fs))
                             (plt:s1 (cadddr fs))
                             n))
               (setq comps (cons e comps))
             )
           )
         )
       )
      )
    )
  )
  (if cur (setq cabs (cons (append cur (list (reverse comps)) (list cseg)) cabs)))
  (setq sd (plt:sdefs tx))
  (list bus vol (reverse cabs) (reverse warns) tb (reverse hdrs) sd)
)

;; ================================================================
;; 三、排槽
;; ================================================================

;; 最小未被占用的槽号（从 1 起找）
(defun plt:freeslot (used / k)
  (setq k 1)
  (while (member k used) (setq k (1+ k)))
  k
)

;; 柜表 -> ((键 . 槽号) ...) 与需要的槽数
;;   键 = 名称 + tab + 型号（同名不同型号各自占槽，与 MCP 口径一致）
;;   def = 本段的槽位顺序定义 ((槽号 . 名称) ...) —— 清单末尾网页生成器
;;         写回的「# 槽位顺序」块（plt:sdefs 解析）；nil = 没写这块，退回老规则
;;   ① 显式槽号先登记（同名冲突取小的）
;;   ② 没给槽号的：先查 def —— 名称命中且那个槽还空着就落这位；
;;      定义里没有的，按首次出现顺序取最小空槽
(defun plt:plan1 (cabs def / map used key k e slot need d sd)
  (setq map nil used nil)
  (setq d (mapcar '(lambda (p) (cons (cdr p) (car p))) def))
  (foreach cab cabs
    (foreach e (nth 7 cab)
      (setq slot (car e))
      (if slot
        (progn
          (setq key (strcat (cadr e) "\t" (caddr e)))
          (setq k (assoc key map))
          (if k
            (if (< slot (cdr k)) (setq map (subst (cons key slot) k map)))
            (setq map (cons (cons key slot) map))
          )
          (if (not (member slot used)) (setq used (cons slot used)))
        )
      )
    )
  )
  (foreach cab cabs
    (foreach e (nth 7 cab)
      (if (null (car e))
        (progn
          (setq key (strcat (cadr e) "\t" (caddr e)))
          (if (null (assoc key map))
            (progn
              (setq sd (cdr (assoc (cadr e) d)))
              (if (and sd (not (member sd used)))
                (setq slot sd)
                (setq slot (plt:freeslot used))
              )
              (setq map (cons (cons key slot) map))
              (setq used (cons slot used))
            )
          )
        )
      )
    )
  )
  (setq need 0)
  (foreach kv map
    (if (> (cdr kv) need) (setq need (cdr kv)))
  )
  (list map need)
)

;; 单段排槽（KYN28 / 只写一条表头行时走这里）
;;   def = 第 1 段的槽位顺序定义（清单末尾「# 槽位顺序」块，nil = 没写）
(defun plt:plan (cabs def) (plt:plan1 cabs def))

;; ================================================================
;; 三·二、分段排槽（箱变两段独立表）
;; ================================================================
;; 【表头行切段】清单里每写一条表头行 = 开始新的一段：
;;   表头 | TMY-50*5 | 10kV           <- 段 1（= 图上最左那枚表头）
;;   @G1 … @BYQ …                    <- 属段 1
;;   表头 | TMY-100*8 N80*8 | 0.4kV  <- 段 2（= 图上最右那枚表头）
;;   @D1 … @D2 …                     <- 属段 2
;; 只写 1 条表头行 -> 1 段 -> 走 plt:plan 老路（KYN28 不受影响）。
;;
;; 【口径】
;;   · 两段【各自从第 1 槽起】编号 —— 同一个槽号在两段是不同元件
;;   · 段内排槽规则与 plt:plan 完全一致（同名同型号共槽、取最小空槽）
;;   · 槽数 = max(各段槽数) —— 块定义共用，只能按最宽那段定
;;   · 表头槽位表【各写各段】：第 j 枚表头只写第 j 段的元件
;;
;; pls = ((段号 map need) …)，段号升序
(defun plt:cseg (cab / sg)
  (setq sg (nth 8 cab))
  (if (and sg (numberp sg) (>= sg 1)) sg 1)
)

(defun plt:segs (cabs / o z sg)
  (setq o nil)
  (foreach z cabs
    (setq sg (plt:cseg z))
    (if (not (member sg o)) (setq o (cons sg o)))
  )
  (reverse o)
)

(defun plt:segc (cabs sg / o z)
  (setq o nil)
  (foreach z cabs
    (if (= (plt:cseg z) sg) (setq o (cons z o)))
  )
  (reverse o)
)

(defun plt:planseg (cabs sdefs / o sg)
  (setq o nil)
  (foreach sg (plt:segs cabs)
    (setq o (cons (cons sg (plt:plan1 (plt:segc cabs sg)
                                      (plt:sdef-at sdefs sg))) o))
  )
  (reverse o)
)

(defun plt:needseg (pls / m x)
  (setq m 0)
  (foreach x pls
    (if (> (caddr x) m) (setq m (caddr x)))
  )
  m
)

(defun plt:maps (pls sg / r x)
  (setq r nil)
  (foreach x pls
    (if (and (null r) (= (car x) sg)) (setq r (cadr x)))
  )
  r
)

;; 槽号 -> 键（反查）
(defun plt:keyat (map k / r)
  (setq r nil)
  (foreach kv map
    (if (and (= (cdr kv) k) (null r)) (setq r (car kv)))
  )
  r
)

;; 本柜 槽号 -> 元件 映射
(defun plt:cabmap1 (cab map / out e key slot)
  (setq out nil)
  (foreach e (nth 7 cab)
    (setq key (strcat (cadr e) "\t" (caddr e)))
    (setq slot (cdr (assoc key map)))
    (if slot (setq out (cons (cons slot e) out)))
  )
  out
)

;; 单段口径（老调用点继续用）
(defun plt:cabmap (cab map) (plt:cabmap1 cab map))

;; 本柜 槽号 -> 元件（单段 / 分段通用）
;;   pls 非 nil（清单写了多条表头行）-> 按本柜段号取那一段的键表
(defun plt:cabget (cab map pls)
  (plt:cabmap1 cab (if pls (plt:maps pls (plt:cseg cab)) map))
)

;; ================================================================
;; 四、图上扫描 / 读写属性
;; ================================================================

;; 块参照的属性表 ((标签 . 属性图元名) ...)
(defun plt:atts (ref / e ed out)
  (setq e (entnext ref) out nil)
  (while (and e (setq ed (entget e)) (= "ATTRIB" (cdr (assoc 0 ed))))
    (setq out (cons (cons (cdr (assoc 2 ed)) e) out))
    (setq e (entnext e))
  )
  (reverse out)
)

;; 属性图元名 -> 文本值（组码 1）
(defun plt:atext (e / ed)
  (setq ed (entget e))
  (plt:s1 (cdr (assoc 1 ed)))
)

;; 属性表里取某标签的**文本值**（没有该标签返回 nil）
;;   注意：plt:atts 给的是「标签 -> 属性图元名」，值还要再取一步组码 1
(defun plt:val (atts tg / p)
  (setq p (assoc tg atts))
  (if p (plt:atext (cdr p)) nil)
)

;; 属性表里 元件NN 的最大槽号（没有则 0）
(defun plt:slotmax (atts / mx tg nn)
  (setq mx 0)
  (foreach a atts
    (setq tg (car a))
    (if (plt:pfx tg *plt:prefix*)
      (progn
        (setq nn (substr tg 5 2))     ; 「元件」= 4 字节，槽号 2 字节
        (if (plt:num nn)
          (if (> (atoi nn) mx) (setq mx (atoi nn)))
        )
      )
    )
  )
  mx
)

;; ---- 表头排序 / 按宽度拆行 / 多行规格落位（2026-09-20 加，为箱变两段）----

;; 表头参照按插入点 x 从小到大排（左 -> 右）
;;   箱变两段靠这个顺序把「第 1 遍表头行」发给最左那枚
(defun plt:hsort (lst / out mn)
  (setq out nil)
  (while lst
    (setq mn (car lst))
    (foreach p lst (if (< (car p) (car mn)) (setq mn p)))
    (setq out (cons (cdr mn) out))
    (setq lst (vl-remove mn lst))
  )
  (reverse out)
)

;; cur 里最后一个可断点的字节下标（空格 / , ; 单字节；、= A1A2 取第 2 字节）
;;   没有可断点返回 nil -> 调用方硬切
(defun plt:lbk (s / i n c r)
  (setq i 1 n (strlen s) r nil)
  (while (< i n)
    (setq c (ascii (substr s i 1)))
    (cond
      ((or (= c 32) (= c 47) (= c 44) (= c 59)) (setq r i) (setq i (1+ i)))
      ((and (= c 161) (= (ascii (substr s (1+ i) 1)) 162))
       (setq r (+ i 1)) (setq i (+ i 2)))
      ((>= c 128) (setq i (+ i 2)))
      (T (setq i (1+ i)))
    )
  )
  r
)

;; 按显示宽度拆行 -> (行1 行2 ...)；断点优先 空格/标点，无断点则硬切
;;   宽度口径与 XBT 算行高完全一致（同一套 *plt:em-ascii* / *plt:slot-col*）
;;   * 断点字符留在**前一行末尾**：空格被 plt:trim 吃掉（等价旧行为），
;;     / , ; 、 则保留 —— 否则「10±2*2.5%/0.4kV」拆行会掉成「10±2*2.5% 0.4kV」
(defun plt:wrap (s w / out cur cw i n c ew step ch lb)
  (setq s (if s s "") out nil cur "" cw 0.0 i 1 n (strlen s))
  (while (<= i n)
    (setq c (ascii (substr s i 1)))
    (if (< c 128) (setq ew *plt:em-ascii* step 1) (setq ew 1.0 step 2))
    (if (and (> (+ cw ew) w) (> (strlen cur) 0))
      (progn
        (setq lb (plt:lbk cur))
        (if lb
          (progn
            (setq out (cons (plt:trim (substr cur 1 lb)) out))
            (setq cur (plt:trim (substr cur (1+ lb))))
            (setq cw (plt:em cur))
          )
          (progn
            (setq out (cons (plt:trim cur) out))
            (setq cur "" cw 0.0)
          )
        )
      )
      (progn
        (setq ch (substr s i step))
        (setq cur (strcat cur ch) cw (+ cw ew) i (+ i step))
      )
    )
  )
  (if (> (strlen cur) 0) (setq out (cons (plt:trim cur) out)))
  (if (null out) (setq out (list "")))
  (reverse out)
)

;; 标签 tg 是不是「槽 k 的规格第 n 行」-> n；元件NN规格（旧单行形态）返回 0
(defun plt:specno (tg k / pre n rest)
  (setq pre (plt:tagk k "规格") n 0)
  (if (and (> (strlen tg) (strlen pre)) (= pre (substr tg 1 (strlen pre))))
    (progn
      (setq rest (substr tg (1+ (strlen pre))))
      (if (and (= (strlen rest) 1) (plt:num rest) (>= (atoi rest) 1))
        (setq n (atoi rest))
      )
    )
  )
  n
)

;; 写一个槽的「规格」-> (写的格数 行数)；行数 0 = 单行标签
;;   多行标签（元件NN规格1..M，XBT 加过行高留下的）按宽度拆成 M 行分别落位；
;;   值不够 M 行的，多余格子写空 —— 幂等，不留残留
(defun plt:putspec (atts k val write / m i n rows hit)
  (setq m 0)
  (foreach a atts
    (setq n (plt:specno (car a) k))
    (if (> n m) (setq m n))
  )
  (if (> m 0)
    (progn
      (setq rows (plt:wrap val *plt:slot-col*) hit 0)
      (foreach i (plt:seq 1 m)
        (if (plt:put atts (plt:tagk k (strcat "规格" (itoa i)))
                     (if (nth (1- i) rows) (nth (1- i) rows) "") write)
          (setq hit (1+ hit))
        )
      )
      ;; (写的格数 格数 实际行数) —— 格数是两段取 max 定的，
      ;;   本柜可能只填了前几行 -> 主流程拿实际行数去居中
      (list hit m (length rows))
    )
    (list (if (plt:put atts (plt:tagk k "规格") val write) 1 0) 0 0)
  )
)

;; 块定义里槽 k 的规格 ATTDEF 各行 y（降序 = 第1行..第m行）
;;   只为取行距 P —— 块定义是标准位，参照被挪过也不影响
(defun plt:srow (bn k / b sub ed tg r n)
  (setq r nil)
  (setq b (tblobjname "BLOCK" bn))
  (setq sub (if b (cdr (assoc -2 (entget b))) nil))
  (while (and sub (/= "ENDBLK" (cdr (assoc 0 (setq ed (entget sub))))))
    (if (= "ATTDEF" (cdr (assoc 0 ed)))
      (progn
        (setq n (plt:specno (cdr (assoc 2 ed)) k))
        (if n (setq r (cons (cons n (caddr (assoc 10 ed))) r)))
      )
    )
    (setq sub (entnext sub))
  )
  (mapcar 'cdr (vl-sort r '(lambda (a b) (> (cdr a) (cdr b)))))
)

;; 实体的 10/11 点 y【一起下移 d】（两点同量，10/11 的相对关系不动）
;;   ★ 不能「直接把 10/11 都设成同一个 y」：属性是 72/74 非零的对正，
;;     实际落点由 11 点（对齐点）决定，10 点只是左基线，两者本来就差
;;     半个字高（实测 11.y = 10.y + 1.5）；都设成同一值会让文字整体
;;     偏 h/2（2026-09-20 实测：规格比数量低 1.5，改成相对位移后逐槽对中）。
;;   ★ 位移按「现值 - 目标值」算 -> 重复跑 d=0，天然幂等。
(defun plt:shdy (ed d / p q out)
  (setq out nil)
  (foreach p ed
    (if (and (member (car p) '(10 11)) (listp (cdr p)) (numberp (car (cdr p))))
      (progn
        (setq q (cdr p))
        (setq out (cons (cons (car p) (list (car q) (- (cadr q) d) (caddr q))) out))
      )
      (setq out (cons p out))
    )
  )
  (reverse out)
)

;; 槽 k 的规格格子有 m 行、本柜只填了 kk 行 -> 把这 kk 行【整组】挪到槽的垂直中心。
;;   锚点 = 该槽「数量」属性的 y（GGH 已把它摆成整槽居中，见 gh:shdn）
;;   行距 P 取块定义里该槽规格行的标准差，不依赖参照现状
;;   位移按【相对】给：把 10/11 一起下移「当前 y - 目标 y」，绝不把两点设成
;;   同一个值（对正不是基线时会把文字整体带偏 h/2 —— 见 plt:shdy）
;;   目标 = 锚点 + P*(kk-1)/2 - P*(n-1) 逐行算，用现值反推位移 -> 重复跑幂等
(defun plt:midrow (ref k m kk / e ed tg cn cy h P ys j n ty d)
  (if (and (> m 0) (> kk 0) (< kk m))
    (progn
      (setq cn (plt:tagk k "数量") cy nil h 3.0)
      (setq e (entnext ref))
      (while (and e (= "ATTRIB" (cdr (assoc 0 (setq ed (entget e))))))
        (setq tg (cdr (assoc 2 ed)))
        (if (= cn tg)
          (progn
            (setq cy (caddr (assoc 10 ed)))
            (setq h (cdr (assoc 40 ed)) h (if h h 3.0))
          )
        )
        (setq e (entnext e))
      )
      (if cy
        (progn
          (setq ys (plt:srow (cdr (assoc 2 (entget ref))) k))
          (setq P (if (and ys (cadr ys)) (- (car ys) (cadr ys)) 6.0))
          (setq e (entnext ref))
          (while (and e (= "ATTRIB" (cdr (assoc 0 (setq ed (entget e))))))
            (setq n (plt:specno (cdr (assoc 2 ed)) k))
            (if (and n (>= n 1) (<= n kk))
              (progn
                (setq ty (- (+ cy (* P (/ (1- kk) 2.0))) (* P (1- n))))
                (setq d (- (caddr (assoc 10 ed)) ty))
                (entmod (plt:shdy ed d))
              )
            )
            (setq e (entnext e))
          )
        )
      )
    )
  )
)

;; 模型空间扫描 -> (柜alist 表头图元表 图上最大槽号)
;;   柜alist = ((柜号 . 块参照图元名) ...)   表头 = (图元名 ...)
;;   靠**标签**认块，不靠块名（GKC 扩容后块名会被污染成 开关柜-AH01-AH01-…）
(defun plt:scan ( / ss i n e atts hd mx k cab hdr)
  (setq cab nil hdr nil mx 0)
  (setq ss (ssget "_X" '((0 . "INSERT") (410 . "Model"))))
  (if ss
    (progn
      (setq i 0 n (sslength ss))
      (while (< i n)
        (setq e (ssname ss i))
        (setq atts (plt:atts e))
        (setq hd (plt:val atts *plt:tag-cab*))
        (cond
          (hd (setq cab (cons (cons hd e) cab)))
          ;; 表头带上插入点 x —— 多表头（箱变两段）靠 x 定左右顺序
          ((assoc *plt:tag-hdr* atts)
           (setq hdr (cons (cons (car (cdr (assoc 10 (entget e)))) e) hdr)))
        )
        (setq k (plt:slotmax atts))
        (if (> k mx) (setq mx k))
        (setq i (1+ i))
      )
    )
  )
  (list (reverse cab) (plt:hsort hdr) mx)
)

;; 写一个标签的值；标签不存在返回 nil。
;;   write = nil 时只探测不落笔（dry 用），返回值仍表示「这一格存在」
(defun plt:put (atts tg val write / p e ed)
  (setq p (assoc tg atts))
  (if (null p)
    nil
    (progn
      (if write
        (progn
          (setq e (cdr p) ed (entget e))
          (if (assoc 1 ed)
            (entmod (subst (cons 1 val) (assoc 1 ed) ed))
            (entmod (append ed (list (cons 1 val))))
          )
          (entupd e)
        )
      )
      T
    )
  )
)

;; ================================================================
;; 四·五、图签 7 格（模型空间的独立 TEXT，不是块属性）
;; ================================================================
;; 实测口径（2026-09-20 量的，别凭记忆改）：
;;   · 图签 = 图框右下角一块 180x28 的格线块，参照插入点 = 图框右边界
;;     （第 n 框 x = (n-1)*470 + 415，y = 5）
;;   · 7 个格子文字是**模型空间的独立 TEXT**（图层 0、字高 3.5/4.0），
;;     每框各一份 —— 所以能逐框写不同内容（表头/柜块是共享定义，做不到）
;;   · 对齐正中（72=4 / 73=2），**组码 11 才是落点、且就是格子中心**；
;;     改字必须连组码 11 一起挪，否则字随字长漂
;;   · 格线块定义里 ATTDEF=0 —— 靠「无属性 + 180x28」认它，不靠块名
;;     （块名 11 是模板给的，换模板会变）

;; 块定义信息（带缓存） -> (ATTDEF数 宽 高 最小x 最小y)
;;   注意：返回的是 cdr(hit)，**没有块名那一项** —— 下标从 ATTDEF 数开始
(setq *plt:defcache* nil)
(defun plt:definfo (bn / hit e b ed ty q c px py x0 y0 x1 y1 na)
  (setq hit (assoc bn *plt:defcache*))
  (if hit
    (cdr hit)
    (progn
      (setq e (tblobjname "BLOCK" bn) na 0 x0 nil x1 nil y0 nil y1 nil)
      (if e
        (progn
          (setq b (entnext e))
          (while (and b (/= "ENDBLK" (cdr (assoc 0 (setq ed (entget b))))))
            (setq ty (cdr (assoc 0 ed)))
            (if (= ty "ATTDEF") (setq na (1+ na)))
            (foreach c (list 10 11)
              (setq q (assoc c ed))
              (if (and q (listp (cdr q)))
                (progn
                  (setq px (car (cdr q)) py (cadr (cdr q)))
                  (if (numberp px)
                    (progn
                      (if (or (null x0) (< px x0)) (setq x0 px))
                      (if (or (null x1) (> px x1)) (setq x1 px))
                      (if (or (null y0) (< py y0)) (setq y0 py))
                      (if (or (null y1) (> py y1)) (setq y1 py))
                    )
                  )
                )
              )
            )
            (setq b (entnext b))
          )
        )
      )
      (if (or (null x0) (null x1))
        (setq hit (list bn na 0.0 0.0 0.0 0.0))
        (setq hit (list bn na (- x1 x0) (- y1 y0) x0 y0))
      )
      (setq *plt:defcache* (cons hit *plt:defcache*))
      (cdr hit)
    )
  )
)

;; 图签格线块参照表 -> ((图元名 插入x 插入y) ...)，按 x 从左到右
(defun plt:tbscan ( / ss i n e ed bn di p out)
  (setq out nil)
  (setq ss (ssget "_X" '((0 . "INSERT") (410 . "Model"))))
  (if ss
    (progn
      (setq i 0 n (sslength ss))
      (while (< i n)
        (setq e (ssname ss i) ed (entget e) bn (cdr (assoc 2 ed)))
        (setq di (plt:definfo bn))
        (if (and (= (nth 0 di) 0)
                 (>= (nth 1 di) 175.0) (<= (nth 1 di) 185.0)
                 (>= (nth 2 di) 24.0) (<= (nth 2 di) 31.0))
          (progn
            (setq p (cdr (assoc 10 ed)))
            (setq out (cons (list e (car p) (cadr p)) out))
          )
        )
        (setq i (1+ i))
      )
    )
  )
  (vl-sort out '(lambda (a b) (< (cadr a) (cadr b))))
)

;; 文字落点：72/73 有非零时组码 11 才是落点，否则用组码 10
(defun plt:tbp (ed / j1 j2 q)
  (setq j1 (assoc 72 ed) j2 (assoc 73 ed))
  (if (and (assoc 11 ed)
           (or (and j1 (/= 0 (cdr j1))) (and j2 (/= 0 (cdr j2)))))
    (progn (setq q (cdr (assoc 11 ed))) (list (car q) (cadr q)))
    (progn (setq q (cdr (assoc 10 ed))) (list (car q) (cadr q)))
  )
)

;; 图签范围内的文字池 -> ((图元名 x y) ...)
(defun plt:tbpool (tx ty / ss i n e p out)
  (setq out nil)
  (setq ss (ssget "_X" '((0 . "TEXT") (410 . "Model"))))
  (if ss
    (progn
      (setq i 0 n (sslength ss))
      (while (< i n)
        (setq e (ssname ss i) p (plt:tbp (entget e)))
        (if (and p
                 (>= (car p) (- tx 182.0)) (<= (car p) (+ tx 2.0))
                 (>= (cadr p) (- ty 2.0)) (<= (cadr p) (+ ty 30.0)))
          (setq out (cons (list e (car p) (cadr p)) out))
        )
        (setq i (1+ i))
      )
    )
  )
  out
)

;; 文字池 -> ((槽位 . 图元名) ...)：先按格子矩形命中，再按格心就近（半径 15）
(defun plt:tbmap (pool tx ty / slots used cell key i it x y x0 x1 y0 y1
                             cx cy best bd d k)
  (setq slots nil used nil)
  (foreach cell *plt:tb-cells*
    (setq key (car cell) x0 (nth 1 cell) x1 (nth 2 cell)
          y0 (nth 3 cell) y1 (nth 4 cell) i 0 k nil)
    (while (and (< i (length pool)) (null k))
      (if (not (member i used))
        (progn
          (setq it (nth i pool) x (- (cadr it) tx) y (- (caddr it) ty))
          (if (and (>= x (- x0 0.5)) (<= x (+ x1 0.5))
                   (>= y (- y0 0.5)) (<= y (+ y1 0.5)))
            (setq k i)
          )
        )
      )
      (setq i (1+ i))
    )
    (if k
      (progn
        (setq slots (cons (cons key (car (nth k pool))) slots))
        (setq used (cons k used))
      )
    )
  )
  ;; 兜底：格心就近（文字落点会被 COM 挪动，实测最大漂 6.0）
  (foreach cell *plt:tb-cells*
    (setq key (car cell))
    (if (null (assoc key slots))
      (progn
        (setq cx (/ (+ (nth 1 cell) (nth 2 cell)) 2.0)
              cy (/ (+ (nth 3 cell) (nth 4 cell)) 2.0)
              best nil i 0)
        (while (< i (length pool))
          (if (not (member i used))
            (progn
              (setq it (nth i pool))
              (setq d (sqrt (+ (expt (- (- (cadr it) tx) cx) 2.0)
                               (expt (- (- (caddr it) ty) cy) 2.0))))
              (if (and (<= d 15.0) (or (null best) (< d bd)))
                (setq best i bd d)
              )
            )
          )
          (setq i (1+ i))
        )
        (if best
          (progn
            (setq slots (cons (cons key (car (nth best pool))) slots))
            (setq used (cons best used))
          )
        )
      )
    )
  )
  slots
)

;; 读一格文字的现值
(defun plt:tbg (e / ed)
  (setq ed (entget e))
  (if (assoc 1 ed) (cdr (assoc 1 ed)) "")
)

;; 写一格文字：值（组码 1）+ 落点（组码 11）；write=nil 只探测
(defun plt:tbput (e cx cy val write / ed)
  (if write
    (progn
      (setq ed (entget e))
      (if (assoc 1 ed)
        (setq ed (subst (cons 1 val) (assoc 1 ed) ed))
        (setq ed (append ed (list (cons 1 val))))
      )
      (if (assoc 11 ed)
        (setq ed (subst (cons 11 (list cx cy 0.0)) (assoc 11 ed) ed))
        (if (assoc 10 ed)
          (setq ed (subst (cons 10 (list cx cy 0.0)) (assoc 10 ed) ed))
        )
      )
      (entmod ed)
      (entupd e)
    )
  )
  T
)

;; 当天 YYYYMMDD（不开 menucmd，直接算，稳）
(defun plt:today ( / d y m dd)
  (setq d (fix (getvar "CDATE")))
  (setq y (/ d 10000))
  (setq m (/ (rem d 10000) 100))
  (setq dd (rem d 100))
  (strcat (itoa y) (if (< m 10) "0" "") (itoa m) (if (< dd 10) "0" "") (itoa dd))
)

;; 柜块参照的插入 x 表（靠「柜号」标签认柜，不认块名）
(defun plt:cabx ( / ss i n e ed out atts)
  (setq out nil)
  (setq ss (ssget "_X" '((0 . "INSERT") (410 . "Model"))))
  (if ss
    (progn
      (setq i 0 n (sslength ss))
      (while (< i n)
        (setq e (ssname ss i) atts (plt:atts e))
        (if (and atts (plt:val atts *plt:tag-cab*))
          (progn
            (setq ed (entget e))
            (setq out (cons (car (cdr (assoc 10 ed))) out))
          )
        )
        (setq i (1+ i))
      )
    )
  )
  out
)

;; 工程号：日期段空 -> 前缀原样；`*` -> 前缀 + 当天；其余照拼
(defun plt:tbproj (pre d)
  (setq pre (if pre pre ""))
  (setq d (if d d ""))
  (if (= pre "")
    ""
    (if (= d "")
      pre
      (if (= d "*")
        (strcat pre (plt:today))
        (strcat pre d)
      )
    )
  )
)

;; 槽位键 -> 取值；nil = 这一格一个字都不写
(defun plt:tbval (key tb qty tot no pno / v)
  (cond
    ((= key "qty")   qty)
    ((= key "total") tot)
    ((= key "no")    no)
    (tb
     (cond
       ((= key "product") (setq v (nth 0 tb)))
       ((= key "title")   (setq v (nth 1 tb)))
       ((= key "code")    (setq v (nth 2 tb)))
       ((= key "project") (setq v pno))
       (T (setq v nil))
     )
     (if (null v) "" v))
    (T nil)
  )
)

;; 图签 7 格 -> 每套图框逐格写
;;   tb    = (柜型 图名 图号 工程号前缀 日期)；nil = 清单没写图签行
;;   write = nil 只算不写
;;   返回 (统计 说明文字)；统计 = (写了几格 实际变了几格 几套)
(defun plt:tbgo (tb write / refs cxs nref idx cnt chg it e e2 tx ty pool m
                              cell key cx cy val old ctl qty tot pno notb)
  (setq refs (plt:tbscan))
  (if (null refs)
    (list nil "  图签：图上没找到图签格线块（先跑 PGT 铺图），没动图。")
    (progn
      (setq cxs (plt:cabx))
      (setq nref (length refs))
      (setq idx 0 cnt 0 chg 0 ctl "")
      ;; 【2026-09-20 改】清单不写「图签」行时不再保留原值：柜型/图名/图号/
      ;;   工程号 4 格一律写空 —— 与 acad-mcp 的 frame_finish 同口径，免得
      ;;   图框模版里别人的预置值（GGD / 进线 D1 / QC… / JX01）被带出去。
      (setq notb (null tb))
      (if notb (setq tb (list "" "" "" "" "")))
      (setq pno (plt:tbproj (nth 3 tb) (nth 4 tb)))
      (foreach it refs
        (setq idx (1+ idx))
        (setq e (car it) tx (cadr it) ty (caddr it))
        (setq pool (plt:tbpool tx ty))
        (setq m (plt:tbmap pool tx ty))
        ;; 数量 = 【项目总柜数】（全图带「柜号」属性的柜块数）—— 2026-09-20 改：
        ;;   原按「本框柜数」逐框数；他纠为「直接填项目总柜数」，各框同值。
        (setq qty (strcat (itoa (length cxs)) "台"))
        (setq tot (itoa nref))
        (foreach cell *plt:tb-cells*
          (setq key (car cell))
          (setq cx (+ tx (/ (+ (nth 1 cell) (nth 2 cell)) 2.0)))
          (setq cy (+ ty (/ (+ (nth 3 cell) (nth 4 cell)) 2.0)))
          (setq val (plt:tbval key tb qty tot (itoa idx) pno))
          (if (not (null val))
            (progn
              (setq e2 (cdr (assoc key m)))
              (if e2
                (progn
                  (setq old (plt:tbg e2))
                  (plt:tbput e2 cx cy val write)
                  (setq cnt (1+ cnt))
                  (if (/= old val) (setq chg (1+ chg)))
                )
                (setq ctl (strcat ctl "第" (itoa idx) "套没配上[" key "]格 "))
              )
            )
          )
        )
      )
      (list
        (list cnt chg nref)
        (strcat "  图签 " (itoa nref) " 套 × 7 格：写 " (itoa cnt)
                " 格（变 " (itoa chg) " 格）"
                (if notb "  清单没写「图签」行 → 柜型/图名/图号/工程号 4 格已清空" "")
                (if (/= ctl "") (strcat SEP "    " ctl) ""))
      )
    )
  )
)

;; ================================================================
;; 五、主流程
;; ================================================================

;; 柜级 6 项（柜号由 PGT 写；这里值非空才写，空的保持原样）
(defun plt:cabfields () '("柜用途" "柜型" "柜尺寸" "容量功率" "分支电流" "备注"))

(defun plt:go (tx write / ps bus vol cabs warns pl map need pls nseg sc cabl hdrl have
                       sl key nm em cnt_cab cnt_slot cnt_hdr cnt_info
                       ncomp cno e atts cbm k val i emv missing cabs2 tbtxt
                       hdrs hi hh hb hv rw hm ex cex sd)
  (setq ps (plt:parse tx))
  (setq bus (car ps) vol (cadr ps) cabs (caddr ps) warns (cadddr ps)
        hdrs (nth 5 ps) sd (nth 6 ps))
  (cond
    ((null cabs)
     (strcat "清单里没解析出柜头行（柜头行必须以 @ 开头），没动图。" SEP
             (if warns (strcat "  " (car warns) SEP) "")))
    (T
     (setq sc (plt:scan) cabl (car sc) hdrl (cadr sc) have (caddr sc))
     (cond
       ((null cabl)
        "图上没找到柜块（先跑 PGT 铺图），没动图。")
       ((null hdrl)
        "图上没找到表头块（先跑 PGT 铺图），没动图。")
       (T
        ;; 图上没有的柜先剔掉再排槽 —— 否则它的元件照样占一个表头槽，
        ;; 排出来是没人用的幽灵槽（名称/型号写进表头，却没有柜用它）
        (setq missing "" cabs2 nil)
        (foreach cab cabs
          (if (assoc (nth 0 cab) cabl)
            (setq cabs2 (cons cab cabs2))
            (setq missing (strcat missing (nth 0 cab) " "))
          )
        )
        (setq cabs (reverse cabs2))
        (cond
         ((null cabs)
          (strcat "清单里的柜在图上一个都找不到（" missing "），没动图。"))
         (T
          ;; 排槽：清单里有几条表头行就是几段
          ;;   1 段 -> 老路 plt:plan（KYN28 不变）
          ;;   ≥2 段 -> 各段独立从第 1 槽起，槽数取两段较大者
          (setq nseg (length (plt:segs cabs)))
          (if (> nseg 1)
            (progn
              (setq pls (plt:planseg cabs sd) map nil need (plt:needseg pls))
            )
            (progn
              (setq pl (plt:plan cabs (plt:sdef-at sd 1))
                    map (car pl) need (cadr pl) pls nil)
            )
          )
          ;; 防呆：清单写了多遍表头行，却没有一段柜落在第 2 遍之后
          ;;   -> 这是【把表头行写在末尾】的旧写法，会静默退化成单段
          ;;      （两枚表头共用同一份槽位表、槽数变成两段之和）
          (if (and hdrs (> (length hdrs) 1) (= nseg 1))
            (setq warns (cons (strcat "清单写了 " (itoa (length hdrs))
                                      " 条表头行，却只切出 1 段 —— 表头行要写在"
                                      "【它那一段的柜之前】，段 = 该表头行之后、"
                                      "下一条表头行之前的柜") warns))
          )
          (setq ncomp 0)
          (foreach cab cabs (setq ncomp (+ ncomp (length (nth 7 cab)))))
          (cond
           ((> need have)
            (strcat "清单需要 " (itoa need) " 槽，图上只有 " (itoa have)
                    " 槽 —— 先用 PGT 按 " (itoa need) " 槽铺图，没动图。"))
           (T
            (setq cnt_cab 0 cnt_slot 0 cnt_hdr 0 cnt_info 0)
        (foreach cab cabs
          (setq cno (nth 0 cab))
          (setq e (cdr (assoc cno cabl)))
          (if (null e)
            (setq missing (strcat missing cno " "))
            (progn
              (setq atts (plt:atts e))
              ;; 柜级 6 项
              (setq i 0)
              (foreach val (plt:cabfields)
                (setq k (nth (+ i 1) cab))
                (if (and k (/= k ""))
                  (if (plt:put atts val k write) (setq cnt_cab (1+ cnt_cab)))
                )
                (setq i (1+ i))
              )
              ;; 槽位：1..have 每槽都写一遍，没数据的写空（幂等、不留残留）
              (setq cbm (plt:cabget cab map pls))
              (foreach k (plt:seq 1 have)
                (setq emv (assoc k cbm))
                ;; 规格：单行标签照旧写一行；加过行高的多行标签（规格1..M）
                ;;   按同一套宽度规则拆行分别落位（XBT 会先把行高加好）
                (setq rw (plt:putspec atts k (if emv (nth 3 (cdr emv)) "") write))
                (setq cnt_slot (+ cnt_slot (car rw)))
                ;; 槽的格数是两段取 max 定的：本柜只填满前 kk 行时，
                ;;   整组规格挪到槽的垂直中心（详见 plt:midrow）
                ;; ★ 只有真写才挪：dry 是只读预演，不能动图元
                (if (and write (caddr rw)) (plt:midrow e k (cadr rw) (caddr rw)))
                (if (plt:put atts (plt:tagk k "数量")
                             (if emv (nth 4 (cdr emv)) "") write)
                  (setq cnt_slot (1+ cnt_slot)))
                ;; 超宽提醒（规格栏 9.0 em）—— 只对单行槽位报；多行槽位本来就该超
                (if (and emv (= (cadr rw) 0)
                         (> (plt:em (nth 3 (cdr emv))) *plt:slot-col*))
                  (setq warns (cons (strcat cno " 元件" (itoa k) " 规格约 "
                                            (rtos (plt:em (nth 3 (cdr emv))) 2 1)
                                            " em，超过 " (rtos *plt:slot-col* 2 1)
                                            " —— 可能压出格子") warns))
                )
              )
            )
          )
        )
        ;; 表头：信息区与槽位表都按【从左到右第几枚】取 ——
        ;;   第 j 枚表头 <-> 清单第 j 条表头行 <-> 第 j 段
        ;;   （分段时各写各段；单段时三处共用同一份键表 = 老行为）
        (setq hi 0)
        (foreach e hdrl
          (setq hi (1+ hi) hb bus hv vol)
          (if (and hdrs (>= (length hdrs) 2))
            (progn
              (setq hh (nth (1- hi) hdrs))
              (if hh (setq hb (car hh) hv (cadr hh)))
            )
          )
          ;; 槽位表【各写各段】：分段时第 hi 枚表头只写第 hi 段的元件；
          ;;   单段时三处共用同一份（老行为）
          (setq hm (if pls (plt:maps pls hi) map))
          (setq atts (plt:atts e))
          (if (/= hb "")
            (if (plt:put atts *plt:tag-hdr* hb write) (setq cnt_info (1+ cnt_info)))
          )
          (if (/= hv "")
            (if (plt:put atts "电压等级" hv write) (setq cnt_info (1+ cnt_info)))
          )
          (foreach k (plt:seq 1 have)
            (setq key (plt:keyat hm k))
            (setq nm (if key (plt:bcut key 9) nil))
            (if (plt:put atts (plt:tagk k "名称") (if nm (car nm) "") write)
              (setq cnt_hdr (1+ cnt_hdr)))
            (if (plt:put atts (plt:tagk k "型号") (if nm (cadr nm) "") write)
              (setq cnt_hdr (1+ cnt_hdr)))
          )
        )
        (if (and pls (/= (length hdrl) nseg))
          (setq warns (cons (strcat "图上表头 " (itoa (length hdrl))
                                    " 枚，清单切出 " (itoa nseg)
                                    " 段 —— 对不上的表头槽位表会写空") warns))
        )
        ;; 图签 7 格（放在灌完柜数据之后 —— 数量格 = 项目总柜数，各框同值）
        (setq tbtxt (cadr (plt:tbgo (nth 4 ps) write)))
        ;; 报告
        (setq sl "")
        (if pls
          (progn
            (foreach ex pls
              (setq sl (strcat sl "段 " (itoa (car ex))
                               "（槽 " (itoa (caddr ex)) "）："))
              (foreach k (plt:seq 1 (caddr ex))
                (setq key (plt:keyat (cadr ex) k))
                (if key (setq sl (strcat sl (itoa k) "=" (car (plt:bcut key 9)) "  ")))
              )
              (setq sl (strcat sl SEP "    "))
            )
          )
          (foreach k (plt:seq 1 need)
            (setq key (plt:keyat map k))
            (if key
              (setq sl (strcat sl (itoa k) "=" (car (plt:bcut key 9)) "  "))
            )
          )
        )
        (strcat
          (if write "已填" "【只算没填】")
          "：柜 " (itoa (length cabs)) " 台 / 元件 " (itoa ncomp) " 条 / 槽位 "
          (itoa need) "（图上 " (itoa have) "）"
          (if (> nseg 1) (strcat "，分段 " (itoa nseg) "（各段独立编号）") "") SEP
          "  " (if write "实写" "将写")
          "：柜级 " (itoa cnt_cab) " 格，柜槽 " (itoa cnt_slot)
          " 格，表头槽 " (itoa cnt_hdr) " 格，表头信息 " (itoa cnt_info) " 格" SEP
          tbtxt SEP
          "  槽位分配：" sl SEP
          (if (/= missing "") (strcat "  图上找不到这些柜：" missing SEP) "")
          (if warns
            (strcat "  警告 " (itoa (length warns)) " 条：" SEP
                    (apply 'strcat (mapcar '(lambda (x) (strcat "    " x SEP)) warns)))
            "")
          (if write "  没存盘，改动都在内存里。" "")
          )
         )
        )
       )
      )
     )
    )
   )
  )
)

;; ================================================================
;; 六、入口
;; ================================================================

(defun plt:run (tx)     (plt:go tx T))
(defun plt:dry (tx)     (plt:go tx nil))
(defun plt:need (tx / ps cabs sd)
  (setq ps (plt:parse tx) cabs (caddr ps) sd (nth 6 ps))
  (if (> (length (plt:segs cabs)) 1)
    (plt:needseg (plt:planseg cabs sd))
    (cadr (plt:plan cabs (plt:sdef-at sd 1)))
  )
)
(defun plt:runfile (f)  (plt:go (plt:readfile f) T))
(defun plt:dryfile (f)  (plt:go (plt:readfile f) nil))
;; 只重填图签（柜数据不动）：柜型|图名|图号|工程号前缀|日期
(defun plt:titlerun (s) (cadr (plt:tbgo (plt:pad (plt:fields s) 5) T)))
(defun plt:titledry (s) (cadr (plt:tbgo (plt:pad (plt:fields s) 5) nil)))

(defun c:PLT ( / f tx r)
  (setq f (getstring T "\n清单文件路径（ANSI/GBK 的 txt，直接回车取消）: "))
  (if (= (plt:trim f) "")
    (princ "\n取消了，什么也没做。")
    (progn
      (setq tx (plt:readfile f))
      (if (null tx)
        (princ (strcat "\n读不到这个文件：" f))
        (progn
          (setq r (plt:go tx T))
          (princ (strcat SEP r))
        )
      )
    )
  )
  (princ)
)

(princ "\n属性块-批量填数.lsp 已加载。命令 PLT（或 (plt:run \"清单文本\") / (plt:titlerun \"GGD|图名|图号|QC\")）。")
(princ)


;;; ================================================================
;;; 模块 六、属性块-一键出图.lsp（CZT，调度层 + 交互入口，命令 CZT）
;;; ================================================================

;;; ================================================================
;;; 属性块-一键出图.lsp          命令：CZT
;;;   一份清单(txt) → 判型 → 铺壳 → 灌数 → 读回，一条命令跑完
;;; ----------------------------------------------------------------
;;; 本文件是【集成调度层】，不重复内核 —— 落地动作全部转发给原有工具：
;;;   铺壳 PGT  属性块-铺图.lsp        箱变 XBT  属性块-箱变.lsp
;;;   灌数 PLT  属性块-批量填数.lsp    改槽 GKC  属性块-槽位增减.lsp
;;;   行高 GGH  属性块-增加行高.lsp    图签 TQ   属性块-填图签.lsp
;;;   元件 JYJ  属性块-增加元件.lsp    柜宽 GKW  属性块-柜宽缩放.lsp
;;;   换槽 CWJH 属性块-槽位顺序.lsp
;;;   按名自动 load：同目录 → 环境变量 CAD_LISP_BASE\lisp → 固定回退路径
;;; ----------------------------------------------------------------
;;; 用法（★ AutoLISP 没有可选参数，少给一个会报「参数太少」）：
;;;   命令 CZT                      打开交互入口（对话框）：
;;;                                   · 「粘贴剪贴板清单 → 一键出图」——
;;;                                     配套的「箱变生成器」「KYN28 生成器」
;;;                                     网页点「写回」会自动把清单复制到
;;;                                     剪贴板（也认手工在别处按同格式复制的
;;;                                     文本），点这个按钮直接出图；
;;;                                   · 「改从 TXT 文件读取…」—— 老的选文件流程；
;;;                                   ★ 出图一律在对话框关掉之后执行：DCL 打开时
;;;                                     跑 command 会取不到输入，把 CAD 卡死。
;;;                                   两个入口都能勾选「只预演」「先清空重铺」、
;;;                                   或强制指定 KYN28 / 箱变两段。
;;;   (czt:auto "D:/x/清单.txt")    给路径、自动判型；返回回包字符串
;;;   (czt:go "路径" nil)           同上（mode 必给：nil = 自动判型）
;;;   (czt:go 路径 "kyn28")         强制 KYN28（PGT 铺壳）
;;;   (czt:go 路径 "xbw")           强制箱变两段（XBT 铺壳）
;;;   (czt:dry 路径)                只预演，不写图
;;;   (czt:go 路径 "wipe")          先 ERASE 当前空间再重铺（危险，必须显式写）
;;;   (czt:text "清单文本" nil)      直接吃文本，不落文件（对话框「粘贴」按钮走这条）
;;;   转发：czt:slot / czt:row / czt:title / czt:add / czt:width / czt:swap
;;; ----------------------------------------------------------------
;;; 规矩：不存盘、不截图；脏图（图上已有柜块）默认拒跑
;;; 判型：清单里「表头」行 >= 2 条 → 箱变两段；否则 KYN28
;;; 本文件编码 ANSI/GBK，无 BOM；
;;; 清单 txt 支持 GBK 与 UTF-8（含/不含 BOM）—— 自动判，不用手动转存
;;; 本文件是【单文件集成版】：把铺图 PGT / 箱变 XBT / 批量填数 PLT /
;;; 槽位增减 GKC / 增加行高 GH 五个依赖模块的源码全部原样并入本文件，
;;; 只用这一个 .lsp 即可运行，不再需要同目录放另外五个文件。
;;; ================================================================
(vl-load-com)

(if (not (boundp 'SEP)) (setq SEP (chr 10)))

;; 回包累积器：czt:say 既打印也累积，入口最后把它当返回值吐出来
(setq *czt:out* "")

;; ================================================================
;; 一、小工具
;; ================================================================

(defun czt:flat (s)
  (if (/= (type s) 'STR) (setq s (vl-princ-to-string s)))
  (if s s "")
)

;; 打印一段回包 + 记进 *czt:out*（多行照打）
(defun czt:say (s / t2)
  (setq t2 (czt:flat s)
        *czt:out* (strcat *czt:out* t2 SEP))
  (princ (strcat SEP t2))
  (princ)
)

;; ----------------------------------------------------------------
;; 读清单文件：GBK / UTF-8（含无 BOM）自适应
;;   判据 = 清单里必有中文关键词「表头」「图签」——
;;   编码用错时这两个词一定解不出来（实测：GBK 文件按 utf-8 读，
;;   两个词全不命中；utf-8 文件按 utf-8 读命中）。
;;   ADODB 读完由 COM 转成系统 ANSI(GBK) 字节串，与 plt:readfile
;;   同一条码路，可以直接喂 plt:run / pgt:run / xbt:run。
;;   纯 ASCII 清单两种解码等价，兜底走 plt:readfile。
;; ----------------------------------------------------------------

;; 按指定 Charset 读文件（COM 不可用 / 读失败返回 nil）
(defun czt:rd1 (f cs / s txt)
  (setq s (vl-catch-all-apply 'vlax-create-object (list "ADODB.Stream")))
  (if (vl-catch-all-error-p s)
    nil
    (progn
      (vl-catch-all-apply 'vlax-put (list s 'Type 2))
      (vl-catch-all-apply 'vlax-put (list s 'Charset cs))
      (vl-catch-all-apply 'vlax-invoke (list s 'Open))
      (vl-catch-all-apply 'vlax-invoke (list s 'LoadFromFile f))
      (setq txt (vl-catch-all-apply 'vlax-invoke (list s 'ReadText -1)))
      (vl-catch-all-apply 'vlax-invoke (list s 'Close))
      (if (or (vl-catch-all-error-p txt) (null txt) (= txt "")) nil txt)
    )
  )
)

;; 解得对不对：清单一定有「表头」或「图签」
(defun czt:okp (s)
  (and (= (type s) 'STR)
       (or (vl-string-search "表头" s) (vl-string-search "图签" s)))
)

;; 清单文件 -> 文本（自适应编码；COM 不可用退回 plt:readfile 的 GBK 路）
(defun czt:readfile (f / tx)
  (setq tx (czt:rd1 f "utf-8"))
  (if (czt:okp tx)
    tx
    (progn
      (setq tx (czt:rd1 f "gb2312"))
      (if (not (czt:okp tx)) (setq tx (plt:readfile f)))
      tx
    )
  )
)

;; ================================================================
;; 二、依赖：按名找 lsp 并 load
;; ================================================================

(defun czt:ld (n / f d p)
  (setq f (findfile (strcat n ".lsp")))
  (if (null f)
    (progn
      (setq d (getenv "CAD_LISP_BASE"))
      (if (or (null d) (= d "")) (setq d "D:/kk三部曲/148.CAD插件研究"))
      (setq f (findfile (strcat d "/lisp/" n ".lsp")))
    )
  )
  (if (null f)
    (setq f (findfile (strcat "D:/kk三部曲/148.CAD插件研究/lisp/" n ".lsp")))
  )
  (if f
    (progn
      (setq p (vl-catch-all-apply 'load (list f)))
      (not (vl-catch-all-error-p p))
    )
    nil
  )
)

;; 函数在不在（atoms-family 两种口径都试，避免符号/字符串比较踩空）
(defun czt:has (n / af)
  (setq af (atoms-family 0))
  (if (or (member n af) (member (read n) af)) T nil)
)

;; 缺哪个补哪个；返回 T，或缺失文件名单（前带空格）
(defun czt:ensure ( / miss m)
  (setq miss "")
  (foreach m '(("PLT:PLAN"    . "属性块-批量填数")
               ("PGT:INS"     . "属性块-铺图")
               ("GKC:REBUILD" . "属性块-槽位增减")
               ("GH:APPLY"    . "属性块-增加行高")
               ("XBT:GO"      . "属性块-箱变"))
    (if (not (czt:has (car m)))
      (if (null (czt:ld (cdr m)))
        (setq miss (strcat miss " " (cdr m)))
      )
    )
  )
  (if (= miss "") T miss)
)

;; 单个模块按需 load（转发族用）
(defun czt:req (fn sym)
  (if (not (czt:has sym)) (czt:ld fn))
  (czt:has sym)
)

;; ================================================================
;; 三、清单解析（只读文本，不改图）
;; ================================================================

;; 模式串 -> 标志表（KYN28 / XBW / DRY / WIPE）
(defun czt:fl (s / u out p)
  (setq u (strcase (if s s "")) out nil)
  (foreach p '("KYN28" "XBW" "BOX" "DRY" "WIPE")
    (if (vl-string-search p u) (setq out (cons p out)))
  )
  (setq out (reverse out))
  (if (member "BOX" out) (setq out (cons "XBW" (vl-remove "BOX" out))))
  out
)

;; 是否注释行（# 或 // 开头，与 plt:parse 的跳过规则同口径 ——
;;   箱变/KYN28 两个网页生成器"写回"时会在清单末尾附一段
;;   "# 槽位顺序（…，仅供核对）" 块，靠这条规则不会被误认成
;;   表头行或柜头行；注意该块同时也是【排槽定义来源】，
;;   由 plt:sdefs 单独解析，不是纯注释）
(defun czt:cmt? (ln) (or (plt:pfx ln "#") (plt:pfx ln "//")))

;; 「表头」行条数 = 段数（跳过注释行）
(defun czt:hdrn (tx / n ln fs)
  (setq n 0)
  (foreach ln (plt:lines tx)
    (if (not (czt:cmt? ln))
      (progn
        (setq fs (plt:fields ln))
        (if (and fs (equal (car fs) "表头")) (setq n (1+ n)))
      )
    )
  )
  n
)

;; 柜号表（@柜头行第一段去掉 @；跳过注释行）
(defun czt:cabs (tx / out ln c)
  (setq out nil)
  (foreach ln (plt:lines tx)
    (if (not (czt:cmt? ln))
      (progn
        (setq c (car (plt:fields ln)))
        (if (and c (= (substr c 1 1) "@") (> (strlen c) 1))
          (setq out (cons (substr c 2) out))
        )
      )
    )
  )
  (reverse out)
)

;; ================================================================
;; 四、图上体检 / 清图
;; ================================================================

;; 图上柜块参照数（口径同 flow.py：块名含「柜块模版」或就是「开关柜」）
(defun czt:oncab ( / ss n i e bn c)
  (setq c 0 ss (ssget "_X" '((0 . "INSERT") (410 . "Model"))))
  (if ss
    (progn
      (setq n (sslength ss) i 0)
      (while (< i n)
        (setq bn (cdr (assoc 2 (entget (ssname ss i)))))
        (if (and bn (or (vl-string-search "柜块模版" bn) (= bn "开关柜")))
          (setq c (1+ c))
        )
        (setq i (1+ i))
      )
    )
  )
  c
)

;; 清空当前空间（危险：只在显式 "wipe" 时走）
(defun czt:wipe ( / ss)
  (setq ss (ssget "_X"))
  (if ss
    (progn
      (vl-catch-all-apply 'vl-cmdf (list "_.ERASE" ss ""))
      (czt:say "  [wipe] 已清空当前空间，准备重铺。")
    )
    (czt:say "  [wipe] 当前空间本来就是空的。")
  )
  (princ)
)

;; ================================================================
;; 五、主流程
;; ================================================================

;; 回包走 *czt:out*，末尾返回它（可与 princ 并行：命令行能看，程序能抓）
(defun czt:ex (tx src mode / fl dry wp kw hd need cabs cc r1 r2 sc res ok)
  (setq *czt:out* "")
  (setq fl  (czt:fl mode)
        dry (if (member "DRY" fl) T nil)
        wp  (if (member "WIPE" fl) T nil))
  (setq hd   (czt:hdrn tx))
  (setq kw   (cond ((member "XBW" fl)   "XBW")
                   ((member "KYN28" fl) "KYN28")
                   ((>= hd 2)           "XBW")
                   (T                   "KYN28")))
  (setq cabs (czt:cabs tx))
  (if cabs (setq need (plt:need tx)))
  (setq cc   (czt:oncab))

  (czt:say (strcat "===== 一键出图 CZT =====" SEP
                   "  清单：" (if src src "（直接给的文本）") SEP
                   "  判型：" (if (= kw "XBW") "箱变两段 → XBT" "KYN28 → PGT")
                   (cond (dry "    [DRY 预演]") (wp "    [WIPE 先清图]") (T "")) SEP
                   "  清单：" (itoa (length cabs)) " 台柜 / " (itoa hd) " 条表头行 / 需 "
                            (itoa (if need need 0)) " 槽" SEP
                   "  图上：柜块 " (itoa cc) " 个"))

  (cond
    ((null cabs)
     (czt:say "[CZT] 清单里没解析出柜头行（柜头行必须以 @ 开头），没动图。"))
    ((and (not dry) (> cc 0) (not wp))
     (czt:say (strcat "[CZT] 脏图拒跑：图上已有 " (itoa cc) " 个柜块（柜块模版-* / 开关柜）。"
                      SEP "       换干净图重跑；确实要清图重铺 → (czt:go \"路径\" \"wipe\")"
                      SEP "       没动图。")))
    (T
     (if wp (czt:wipe))
     (if dry
       (progn
         (czt:say "—— 预演（不写图）——")
         (if (= kw "XBW") (czt:say (xbt:dry tx)) (czt:say (pgt:dry need cabs)))
         (if (> cc 0)
           (czt:say (plt:dry tx))
           (czt:say "（空图：PLT 预演跳过 —— 它要先有柜块才算得出灌数；正式跑会先铺壳再灌数）")
         )
         (czt:say "== 预演结束，图没动 ==")
       )
       (progn
         (czt:say (strcat "—— 1/3 铺壳 " (if (= kw "XBW") "XBT（箱变两段）" "PGT") " ——"))
         (setq r1 (if (= kw "XBW") (xbt:run tx) (pgt:run need cabs)))
         (czt:say r1)
         (czt:say "—— 2/3 灌数 PLT（柜数据 + 表头 + 图签）——")
         (setq r2 (plt:run tx))
         (czt:say r2)
         (setq sc  (plt:scan)
               res (list (length (car sc)) (length (cadr sc)) (caddr sc)))
         (setq ok  (and (= (car res) (length cabs)) (= (caddr res) (if need need 0))))
         (czt:say (strcat "—— 3/3 读回 ——" SEP
                          "  图上：柜 " (itoa (car res)) " 台 / 表头 " (itoa (cadr res))
                          " 枚 / 槽位 " (itoa (caddr res)) SEP
                          "  期望：柜 " (itoa (length cabs)) " 台 / 槽位 " (itoa (if need need 0)) SEP
                          "  结果：" (if ok "OK 对齐" "CHECK 对不上，看上面回包")))
       )
     )
    )
  )
  *czt:out*
)

;; 给文件路径
(defun czt:go (f mode / tx mm)
  (setq *czt:out* "")
  (if (czt:dcl-open?)
    (czt:say "[CZT] 对话框还开着，拒绝出图（DCL 状态下跑 command 会把 CAD 锁死）。先关掉对话框再试。")
  (if (or (null f) (= f ""))
    (czt:say "[CZT] 没给清单路径。用法 (czt:go \"D:/x/清单.txt\")。")
    (progn
      (setq mm (czt:ensure))
      (if (/= mm T)
        (czt:say (strcat "[CZT] 缺工具文件（同目录没找到）：" mm
                         SEP "       没动图。"))
        (progn
          (setq tx (czt:readfile f))
          (if (null tx)
            (czt:say (strcat "[CZT] 读不到这个文件：" f))
            (czt:ex tx f mode)
          )
        )
      )
    )
  )
  )
  *czt:out*
)

;; 只给路径（mode = nil，自动判型）—— 一参快捷入口
(defun czt:auto (f)
  (czt:go f nil)
)

;; 直接给文本
(defun czt:text (tx mode / mm)
  (setq *czt:out* "")
  (if (czt:dcl-open?)
    (czt:say "[CZT] 对话框还开着，拒绝出图（DCL 状态下跑 command 会把 CAD 锁死）。先关掉对话框再试。")
    (progn
      (setq mm (czt:ensure))
      (if (/= mm T)
        (czt:say (strcat "[CZT] 缺工具文件（同目录没找到）：" mm SEP "       没动图。"))
        (czt:ex tx nil mode)
      )
    )
  )
  *czt:out*
)

;; 只预演
(defun czt:dry (f)
  (czt:go f "dry")
)

;; ================================================================
;; 六、其余工具功能的统一转发（不留死角）
;; ================================================================

;; 改槽 GKC：(czt:slot "句柄,…" ±N)
(defun czt:slot (s k / r)
  (setq r (if (czt:req "属性块-槽位增减" "GKC:EXPAND")
            (gkc:expand s k)
            "[CZT] 没找到 属性块-槽位增减.lsp"))
  (czt:say r)
  r
)

;; 加行高 GGH：(czt:row "句柄,…" "1,3,1")
(defun czt:row (s k / r)
  (setq r (if (czt:req "属性块-增加行高" "GH:APPLY")
            (gh:apply s k)
            "[CZT] 没找到 属性块-增加行高.lsp"))
  (czt:say r)
  r
)

;; 只填图签 TQ：(czt:title "柜型|图名|图号|工程号前缀|日期")
(defun czt:title (s / r)
  (setq r (if (czt:req "属性块-填图签" "TQ:RUN")
            (tq:run s)
            "[CZT] 没找到 属性块-填图签.lsp"))
  (czt:say r)
  r
)

;; 加一个元件 JYJ：(czt:add "柜号|名称|型号|规格|数量")
(defun czt:add (s / r)
  (setq r (if (czt:req "属性块-增加元件" "JYJ:ADD")
            (jyj:add s)
            "[CZT] 没找到 属性块-增加元件.lsp"))
  (czt:say r)
  r
)

;; 柜宽缩放 GKW：(czt:width "句柄,…" 倍数)
(defun czt:width (s k / r)
  (setq r (if (czt:req "属性块-柜宽缩放" "GKW:BYREFS")
            (gkw:byrefs s k)
            "[CZT] 没找到 属性块-柜宽缩放.lsp"))
  (czt:say r)
  r
)

;; 两个槽位对调 CWJH：(czt:swap "3 4")
(defun czt:swap (s / r)
  (setq r (if (czt:req "属性块-槽位顺序" "CWJH:RUN")
            (cwjh:run s)
            "[CZT] 没找到 属性块-槽位顺序.lsp"))
  (czt:say r)
  r
)

;; ================================================================
;; 七、剪贴板读取与交互界面（粘贴一键出图）
;; ================================================================
;; DCL 原生控件没有"可粘贴的多行文本框"，所以交互入口的"粘贴"采用
;; CAD 插件里最常见的做法：配套的「箱变生成器」「KYN28 生成器」网页点一下
;; 「写回」按钮，会把整理好的清单文本自动复制到 Windows 剪贴板；回到本
;; 对话框点按钮，程序直接从剪贴板取文本 —— 对用户来说仍然是"点一下写回、
;; 再点一下出图"，只是"粘贴"动作发生在点按钮那一刻，而不是敲进某个输入框。
;; 本机同样接受不经那两个网页、手工按同一格式整理好后复制来的文本。
;; 对话框本身（DCL）在运行时生成到系统临时目录，用完即删 —— 不需要
;; 随本文件再带一份 .dcl，整套工具仍然只有【一个】.lsp 文件。

;; 读取剪贴板文本 —— 两级方案，任何一级拿到非空文本即返回：
;;   ① PowerShell + System.Windows.Forms.Clipboard（首选，最稳）
;;      旧版只走 htmlfile.parentWindow.clipboardData，那条路依赖 IE 的
;;      "允许通过脚本访问剪贴板"安全设置：Win10/11 上要么弹确认框、要么
;;      直接返回空/报错（新版 CAD 的 COM 环境里尤其常见），所以不能单靠它。
;;      这里让 PowerShell 隐藏运行，把剪贴板文本以 UTF-8 写到临时文件，
;;      再用 czt:rd1（ADODB）读回来 —— 中文不会乱码，也不弹任何窗口。
;;   ② htmlfile（原方案，留作兜底：没有 PowerShell 的老系统可用）
;; 读不到 / 剪贴板不是文本 / 剪贴板是空的 -> 返回 nil。

(defun czt:clip-ps ( / sh tmp cmd txt)
  (setq tmp (vl-string-translate "/" "\\" (vl-filename-mktemp "czt_clip" nil ".txt")))
  (if (findfile tmp) (vl-file-delete tmp))
  (setq sh (vl-catch-all-apply 'vlax-create-object (list "WScript.Shell")))
  (if (vl-catch-all-error-p sh)
    nil
    (progn
      (setq cmd
        (strcat
          "powershell.exe -NoProfile -STA -ExecutionPolicy Bypass -Command \""
          "Add-Type -AssemblyName System.Windows.Forms; "
          "$t=[System.Windows.Forms.Clipboard]::GetText([System.Windows.Forms.TextDataFormat]::UnicodeText); "
          "[System.IO.File]::WriteAllText('" tmp "',$t,(New-Object System.Text.UTF8Encoding($true)))"
          "\""))
      ;; 0 = 隐藏窗口；:vlax-true = 等它跑完再往下
      (vl-catch-all-apply 'vlax-invoke-method (list sh 'Run cmd 0 :vlax-true))
      (vl-catch-all-apply 'vlax-release-object (list sh))
      (setq txt (if (findfile tmp) (czt:rd1 tmp "utf-8") nil))
      (if (findfile tmp) (vl-file-delete tmp))
      (if (and (= (type txt) 'STR) (/= txt "")) txt nil)
    )
  )
)

(defun czt:clip-html ( / htm win cbd txt)
  (setq htm (vl-catch-all-apply 'vlax-get-or-create-object (list "htmlfile")))
  (if (vl-catch-all-error-p htm)
    nil
    (progn
      (setq win (vl-catch-all-apply 'vlax-get-property (list htm 'parentwindow)))
      (setq cbd (if (vl-catch-all-error-p win)
                  nil
                  (vl-catch-all-apply 'vlax-get-property (list win 'clipboarddata))
                ))
      (setq txt (if (or (null cbd) (vl-catch-all-error-p cbd))
                  nil
                  (vl-catch-all-apply 'vlax-invoke-method (list cbd 'getdata "Text"))
                ))
      (vl-catch-all-apply 'vlax-release-object (list htm))
      (if (or (null txt) (vl-catch-all-error-p txt) (/= (type txt) 'STR) (= txt ""))
        nil
        txt
      )
    )
  )
)

(defun czt:clip ( / tx)
  (setq tx (czt:clip-ps))
  (if (null tx) (setq tx (czt:clip-html)))
  tx
)

;; ----------------------------------------------------------------
;; 反向：文本 -> 剪贴板（与 czt:clip-ps 对称的第二套通道）
;;   文本先用 ADODB 按 utf-8 落到临时文件，再让 PowerShell 读回并
;;   Clipboard::SetText —— 绕这一圈是因为清单里含 | @ # 换行和中文，
;;   直接拼进 powershell -Command 的命令行会被引号/转义吃掉，必变形。
;;   为什么敢在对话框回调里跑：读剪贴板走的就是同一条
;;   WScript.Shell 同步 Run，实测在 DCL 打开状态下正常返回、不卡死；
;;   这条只是把 GetText 换成 SetText，同样不碰 CAD 命令行。
;; ----------------------------------------------------------------

;; 按 utf-8 写文本文件（COM 不可用 / 写失败返回 nil）
(defun czt:wr1 (tx f / s r)
  (if (findfile f) (vl-file-delete f))
  (setq s (vl-catch-all-apply 'vlax-create-object (list "ADODB.Stream")))
  (if (vl-catch-all-error-p s)
    nil
    (progn
      (vl-catch-all-apply 'vlax-put (list s 'Type 2))
      (vl-catch-all-apply 'vlax-put (list s 'Charset "utf-8"))
      (vl-catch-all-apply 'vlax-invoke (list s 'Open))
      (vl-catch-all-apply 'vlax-invoke (list s 'WriteText tx))
      ;; 2 = adSaveCreateOverWrite
      (setq r (vl-catch-all-apply 'vlax-invoke (list s 'SaveToFile f 2)))
      (vl-catch-all-apply 'vlax-invoke (list s 'Close))
      (if (and (not (vl-catch-all-error-p r)) (findfile f)) T nil)
    )
  )
)

;; 文本 -> 剪贴板（成功 T）。空文本直接拒。
(defun czt:clip-set (tx / tmp ok sh cmd rc)
  (setq tx (czt:flat tx))
  (if (= tx "")
    nil
    (progn
      (setq tmp (vl-string-translate "/" "\\" (vl-filename-mktemp "czt_pb" nil ".txt")))
      (setq ok (czt:wr1 tx tmp))
      (if ok
        (progn
          (setq sh (vl-catch-all-apply 'vlax-create-object (list "WScript.Shell")))
          (if (vl-catch-all-error-p sh)
            (setq ok nil)
            (progn
              (setq cmd
                (strcat
                  "powershell.exe -NoProfile -STA -ExecutionPolicy Bypass -Command \""
                  "Add-Type -AssemblyName System.Windows.Forms; "
                  "$t=[System.IO.File]::ReadAllText('" tmp "',[System.Text.Encoding]::UTF8); "
                  "[System.Windows.Forms.Clipboard]::SetText($t,[System.Windows.Forms.TextDataFormat]::UnicodeText); "
                  "[System.IO.File]::WriteAllText('" tmp ".ok','ok')"
                  "\""))
              ;; 0 = 隐藏窗口；:vlax-true = 等它跑完
              (setq rc (vl-catch-all-apply 'vlax-invoke-method (list sh 'Run cmd 0 :vlax-true)))
              (vl-catch-all-apply 'vlax-release-object (list sh))
              (setq ok (and (not (vl-catch-all-error-p rc))
                            (= (type rc) (quote INT))
                            (= rc 0)))
              ;; 退出码拿不到时，看 PowerShell 末尾写的哨兵
              (if (null ok) (setq ok (if (findfile (strcat tmp ".ok")) T nil)))
              (if (findfile (strcat tmp ".ok")) (vl-file-delete (strcat tmp ".ok")))
            )
          )
        )
      )
      (if (findfile tmp) (vl-file-delete tmp))
      ok
    )
  )
)

;; ================================================================
;; 反向导出：当前图纸 -> 清单文本（纯只读，不动图）
;;   扫模型空间的**属性块**（柜块 / 表头块）与图签 TEXT，按 CZT 支持的
;;   清单格式原样拼回来 —— 与「粘贴剪贴板清单 -> 出图」正好反向。
;;   产物直接喂 CZT / PLT 能跑，粘回网页生成器也能再编辑。
;;
;;   口径（与正向对称，不认块名、只认标签）：
;;     · 柜块   = 带「柜号」标签的 INSERT
;;     · 表头块 = 带「主母线规格」标签的 INSERT
;;     · 柜级 6 项     读柜块：柜用途 / 柜型 / 柜尺寸 / 容量功率 / 分支电流 / 备注
;;     · 元件名称/型号  读**表头块**槽位（元件NN名称 / 元件NN型号）
;;     · 元件规格/数量  读**柜块**槽位（元件NN规格[1..M] / 元件NN数量）
;;     · 图签行        读模型空间独立 TEXT（plt:tbscan / tbpool / tbmap 反查）
;;   分段：按槽号回绕切段（见下面「段信息说明」），第 si 段 <-> 从左到右第 si
;;   枚表头块 —— 箱变两段完整还原成两条表头行 + 各自元件。
;;   元件行【不写槽号】：PLT 按「名称+型号」认槽，顺序不参与定位，所以省掉
;;   槽号也能回灌得一模一样，且与网页生成器写回的格式对齐。
;;   多行规格（元件NN规格1..M，XBT 加过行高）：按行拼接，行间补一个空格。
;;   全程 ssget / entget，**不做任何 entmod**，可在对话框里安全跑。
;; ================================================================

;; 导出摘要 / 失败原因（czt:dump 顺带写，给界面与回包用）
(setq *czt:dump-msg* "")

;; 柜表 -> ((x 柜号 图元名) ...) 按 x 升序（左 -> 右 = 图上的段顺序）
(defun czt:dump-cabs (cabl / out ce x)
  (setq out nil)
  (foreach c cabl
    (setq ce (cdr c) x (car (cdr (assoc 10 (entget ce)))))
    (if (numberp x) (setq out (cons (list x (car c) ce) out)))
  )
  (vl-sort out '(lambda (a b) (< (car a) (car b))))
)

;; 段信息说明（2026-09-24 二次修正）：
;;   先前那句「段边界在图上不可恢复」是**错的**。判段的真依据是**槽号回绕**：
;;   正向 plt:planseg 给每段独立从第 1 槽起编号（高压段 G1 占 1-3、G2 占 4-5、
;;   BYQ1 占 6；低压段 D1 又从 1 重来占 1-2、D2 占 3），所以只要某柜的最小槽号
;;   <= 前面见过的最大槽号，就是回绕 = 新段开始。
;;   段序 = 从左到右，第 si 段 <-> 从左到右第 si 枚表头块 —— 两段箱变因此能
;;   **完整还原**成两条表头行 + 各自元件（含低压柜自己的名称/型号）。
;;   柜块之间确实没有几何间隙，但那已经不需要了。

;; 取一个槽的规格：有多行标签（元件NN规格1..M）就 1..M 拼回来，否则读单行标签。
;;   行间补一个空格 —— wrap 拆行时会把断点处的空白 trim 掉，拼回来只能近似
;;   （只有超宽被拆行的规格才走这条路，普通规格不受影响）
;; 表头块表 -> ((x 属性表) ...) 按 x 升序（左 -> 右 = 段序）
;;   plt:scan 的表头表元素是**图元名**（plt:hsort 把 x 丢了），所以在这里自己取 x。
(defun czt:dump-hs (hdrl / out h x)
  (setq out nil)
  (foreach h hdrl
    (setq x (car (cdr (assoc 10 (entget h)))))
    (if (numberp x) (setq out (cons (list x (plt:atts h)) out)))
  )
  (vl-sort out '(lambda (a b) (< (car a) (car b))))
)

;; 本柜【有数据的槽号】（规格或数量至少一个非空），升序
;;   空槽不出行 —— 生成器写回的清单里就没有空元件行
(defun czt:dump-slots (atts / out mx k sp qt)
  (setq out nil mx (plt:slotmax atts))
  (foreach k (plt:seq 1 mx)
    (setq sp (czt:dump-spec atts k))
    (setq qt (plt:val atts (plt:tagk k "数量")))
    (if (not (and (= (czt:flat sp) "") (= (czt:flat qt) "")))
      (setq out (cons k out))
    )
  )
  (reverse out)
)

;; 工程号「前缀 + 日期」成品 -> (前缀 日期)
;;   plt:tbproj 本来就是 strcat 两段成品的，所以拆开再拼回**值不变**。
;;   只认尾部 10 位 YYYY-MM-DD，或 8 位 20 开头的 YYYYMMDD；认不出就整串当前缀。
(defun czt:dump-pno (s / n d t10 t8)
  (setq s (if s s "") n (strlen s) d nil)
  (if (>= n 10)
    (progn
      (setq t10 (substr s (- n 9)))
      (if (and (= (substr t10 5 1) "-") (= (substr t10 8 1) "-")
               (plt:num (substr t10 1 4)) (plt:num (substr t10 6 2))
               (plt:num (substr t10 9 2)))
        (setq d t10)
      )
    )
  )
  (if (and (null d) (>= n 8))
    (progn
      (setq t8 (substr s (- n 7)))
      (if (and (plt:num t8) (= (substr t8 1 2) "20")) (setq d t8))
    )
  )
  (if d (list (substr s 1 (- n (strlen d))) d) (list s ""))
)

;; 柜表 -> 分段 ((柜 ...) ...)，段序 = 从左到右
;;   段内槽号是**全局连续**的：G1 占 1-3、G2 占 4-5、BYQ1 占 6；第二段 D1 又从 1
;;   重来占 1-2、D2 占 3。所以「本柜最小槽号 <= 前面见过的最大槽号」= 槽号回绕
;;   = 新段开始。这条与正向 plt:planseg 正好互逆（那边是清单里一条表头行切一段）。
;;   ★ 新段必须把 mx 归零 —— 否则第二段之后每台柜都会被当成又一段。
;;   柜块之间没有几何间隙 —— 判段不靠几何，靠槽号。
(defun czt:dump-segs (cabs / out cur mx ks mi k)
  (setq out nil cur nil mx 0)
  (foreach c cabs
    (setq ks (czt:dump-slots (plt:atts (nth 2 c))))
    (if (null ks)
      (setq cur (append cur (list c)))
      (progn
        (setq mi (apply 'min ks))
        (if (and cur (> mi mx))
          (setq cur (append cur (list c)))
          (progn
            (if cur (setq out (append out (list cur))))
            (setq cur (list c) mx 0)
          )
        )
        (foreach k ks (if (> k mx) (setq mx k)))
      )
    )
  )
  (if cur (setq out (append out (list cur))))
  out
)

(defun czt:dump-spec (atts k / m n a i v s)
  (setq m 0)
  (foreach a atts
    (setq n (plt:specno (car a) k))
    (if (> n m) (setq m n))
  )
  (if (> m 0)
    (progn
      (setq s "")
      (foreach i (plt:seq 1 m)
        (setq v (plt:val atts (plt:tagk k (strcat "规格" (itoa i)))))
        (if (and v (/= v ""))
          (setq s (if (= s "") v (strcat s " " v)))
        )
      )
      s
    )
    (progn
      (setq v (plt:val atts (plt:tagk k "规格")))
      (if v v "")
    )
  )
)

;; 图签：key -> 文字内容
(defun czt:dump-tv (m key / p)
  (setq p (assoc key m))
  (if p (plt:tbg (cdr p)) "")
)

;; 图签 -> (柜型 图名 图号 工程号)；4 格全空 / 找不到图签块 -> nil
;;   工程号格图上存的是**拼好的成品**（前缀 + 日期），导回来当前缀用、日期段
;;   留空 -> 再出图时照拼，值不变
;; 图签 -> (柜型 图名 图号 工程号前缀 日期)；5 段全空 / 找不到图签块 -> nil
;;   图上「工程号」格存的是 plt:tbproj 拼好的成品（前缀+日期），这里拆回两段，
;;   好跟网页生成器写回的 `图签|柜型|图名|图号|前缀|日期` 对上。
(defun czt:dump-title ( / refs r tx ty pool m o pr)
  (setq refs (plt:tbscan))
  (if (null refs)
    nil
    (progn
      (setq r (car refs) tx (cadr r) ty (caddr r))
      (setq pool (plt:tbpool tx ty))
      (setq m (plt:tbmap pool tx ty))
      (setq o (list (czt:dump-tv m "product") (czt:dump-tv m "title")
                    (czt:dump-tv m "code")))
      (setq pr (czt:dump-tv m "project"))
      (setq o (append o (czt:dump-pno pr)))
      (if (and (= (nth 0 o) "") (= (nth 1 o) "") (= (nth 2 o) "")
               (= (nth 3 o) "") (= (nth 4 o) ""))
        nil o)
    )
  )
)

;; 一行：段间用 | 连，不足 n 段补空（空段有意义，PLT 靠位置认字段）
(defun czt:dump-line (lst n / out i v)
  (setq out "" i 0)
  (foreach v lst
    (setq i (1+ i))
    (setq out (strcat out (if (= i 1) "" "|") (if v v "")))
  )
  (while (< i n)
    (setq out (strcat out "|") i (1+ i))
  )
  out
)

;; ----------------------------------------------------------------
;; 主入口：图纸 -> 清单文本（CRLF 分行）。没数据返回 nil，原因在 *czt:dump-msg*
;; ----------------------------------------------------------------
;; ----------------------------------------------------------------
;; 主入口：图纸 -> 清单文本（CRLF 分行）。没数据返回 nil，原因在 *czt:dump-msg*
;;   产物与网页生成器写回的清单**同构**：图签行在最前，每段一条表头行，
;;   柜头行 + 该柜元件行（名称|型号|规格|数量，无槽号，空槽不出行）。
;; ----------------------------------------------------------------
(defun czt:dump ( / NL sc cabl hdrl have cabs hs segs tb txt ncomp nseg
                    si seg hp hatt atts fs ks k nm md sp qt)
  (setq NL (strcat (chr 13) (chr 10)))
  (setq sc (plt:scan))
  (setq cabl (car sc) hdrl (cadr sc) have (caddr sc))
  (cond
    ((and (null cabl) (null hdrl))
     (setq *czt:dump-msg* "图上既没柜块也没表头块（先 PGT / XBT 铺图）。")
     nil)
    ((null cabl)
     (setq *czt:dump-msg* (strcat "图上没找到柜块（柜块要有「" *plt:tag-cab* "」标签）。"))
     nil)
    ((null hdrl)
     (setq *czt:dump-msg* (strcat "图上没找到表头块（表头要有「" *plt:tag-hdr* "」标签）。"))
     nil)
    (T
     (setq cabs (czt:dump-cabs cabl))
     (setq hs (czt:dump-hs hdrl))
     (setq segs (czt:dump-segs cabs))
     (setq nseg (length segs))
     (setq txt "" ncomp 0)
     ;; 图签行【放最前】—— 与网页生成器写回的清单同序
     (setq tb (czt:dump-title))
     (if tb (setq txt (strcat txt (czt:dump-line (append (list "图签") tb) 6) NL)))
     (setq si 0)
     (foreach seg segs
       (setq si (1+ si))
       ;; 表头行：第 si 段 <-> 从左到右第 si 枚表头块
       ;;   （正向 plt:maps pls hi 写的就是这个对应，这里取反）
       (setq hp (nth (1- si) hs) hatt (if hp (cadr hp) nil))
       (setq txt (strcat txt (czt:dump-line
                    (list "表头"
                          (if hatt (plt:val hatt *plt:tag-hdr*) "")
                          (if hatt (plt:val hatt "电压等级") "")) 3) NL))
       (foreach c seg
         (setq atts (plt:atts (nth 2 c)))
         ;; 柜头行：@柜号 | 柜用途 | 柜型 | 柜尺寸 | 容量功率 | 分支电流 | 备注
         (setq fs (list (strcat "@" (nth 1 c))))
         (foreach f (plt:cabfields) (setq fs (append fs (list (plt:val atts f)))))
         (setq txt (strcat txt (czt:dump-line fs 7) NL))
         ;; 元件行：名称 | 型号 | 规格 | 数量（**无槽号**）
         ;;   名称/型号 <- 本段表头块槽位；规格/数量 <- 本柜槽位；空槽不出行。
         ;;   PLT 回灌是按「名称+型号」认槽的，顺序不参与定位，所以省掉槽号照样对得上。
         (foreach k (czt:dump-slots atts)
           (setq nm (if hatt (plt:val hatt (plt:tagk k "名称")) ""))
           (setq md (if hatt (plt:val hatt (plt:tagk k "型号")) ""))
           (setq sp (czt:dump-spec atts k))
           (setq qt (plt:val atts (plt:tagk k "数量")))
           (setq txt (strcat txt (czt:dump-line (list nm md sp qt) 4) NL))
           (setq ncomp (1+ ncomp))
         )
       )
     )
     (setq *czt:dump-msg*
       (strcat "段 " (itoa nseg) " / 柜 " (itoa (length cabs))
               " 台 / 表头 " (itoa (length hdrl)) " 枚 / 元件 " (itoa ncomp) " 条"
               (if tb " / 图签已带" " / 无图签")))
     txt
    )
  )
)

;; 图纸 -> 清单 -> 剪贴板（返回给人看的回包字符串）
(defun czt:dumpclip ( / tx ok)
  (setq tx (czt:dump))
  (if (null tx)
    (strcat "[CZT] 图上没扫到可导出的数据 —— " *czt:dump-msg*)
    (progn
      (setq ok (czt:clip-set tx))
      (if ok
        (strcat "[CZT] 已把图上数据导出成清单并写回剪贴板（" *czt:dump-msg* "）。"
                SEP "      格式与 CZT / PLT 吃的清单一致，直接粘回网页生成器也能再编辑。")
        (strcat "[CZT] 导出成功但写剪贴板失败（PowerShell 那条路没走通）。"
                SEP "      文本没丢：命令行执行 (czt:dump) 可直接取到。"))
    )
  )
)

;; 命令行版：图纸 -> 清单 -> 剪贴板（对话框外重试 / 脚本调用）
(defun czt:cur-clip ( / tx)
  (setq tx (czt:dump))
  (if tx (czt:clip-set tx) nil)
)

;; 把对话框上「判型 / 预演 / 清图」三组控件拼成 czt:fl 能识别的 mode 串
;; ----------------------------------------------------------------
;; 对话框开着时禁止出图（硬保护）
;;   实测（2026-09-24）：DCL 对话框处于打开状态时执行出图会卡死整个 CAD ——
;;   PGT/XBT/PLT 内部大量 (command "_.INSERT" …) / (command "_.ZOOM" …)，
;;   而对话框打开时命令行输入被 DCL 消息循环接管，command 取不到输入 →
;;   主线程死等 → 界面完全无响应，只能杀进程。
;;   所以：按钮回调里只「取数据 + 校验 + 关对话框」，
;;         真正的出图统一放到 start_dialog 返回之后（czt:ui-exec）。
;; ----------------------------------------------------------------
(setq *czt:dcl* nil)
(setq *czt:ui-job* nil)

;; 「当前清单」：最近一次加载成功的那份，形如 (来源 文本)
;;   来源 = "剪贴板" 或 txt 的文件名（不含扩展名）
;;   文本 = 原文，字节级照搬，不加工
;;   写回剪贴板按钮就取它。程序级状态，跨对话框保留（重新 load 才清）。
(setq *czt:ui-cur* nil)

(defun czt:dcl-open? () (and (boundp '*czt:dcl*) *czt:dcl*))

;; 取控件值并兜底：get_tile 对容器/不存在的 key 会返 nil，
;;   （AutoLISP 无 stringp 保护会直接崩「参数类型错误: stringp nil」）
(defun czt:tile (k / v)
  (setq v (get_tile k))
  (if (= (type v) (quote STR)) v "")
)

(defun czt:ui-flags ( / ms fl)
  ;; 判型：radio_column 的 key 取不到值，必须读 radio_button 自己的 key
  (setq ms (cond
             ((= (czt:tile "m_kyn28") "1") "kyn28")
             ((= (czt:tile "m_xbw")   "1") "xbw")
             (T "")
           ))
  (setq fl ms)
  (if (= (czt:tile "dry")  "1") (setq fl (strcat fl " dry")))
  (if (= (czt:tile "wipe") "1") (setq fl (strcat fl " wipe")))
  fl
)

;; 把回包（多行文本）铺进对话框的日志列表
(defun czt:ui-log (s / lns x)
  (setq lns (plt:lines (czt:flat s)))
  (start_list "log")
  (foreach x lns (add_list x))
  (end_list)
)

;; 「粘贴剪贴板清单 → 一键出图」按钮
;;   czt:okp 已经是判"清单像不像样"的现成标准（找「表头」或「图签」关键字，
;;   跟 czt:readfile 判文件编码用的是同一条规则）——这里直接拿来先做一次
;;   粘贴内容的形态检查，能在跑之前就拦住"复制错了/忘了点写回"这类误粘贴，
;;   给出比"跑到一半才报错"更直接的提示。
;;   箱变/KYN28 两个网页生成器的"写回"按钮本就是照 czt 这套格式拼的文本
;;   （图签/表头 用 | 分隔、柜头行 @ 开头、元件行 名称|型号|规格|数量、
;;   末尾可能带一段 # 开头的槽位顺序核对块），czt:okp 通不过基本就是
;;   粘贴的不是这两个工具"写回"出来的内容。
(defun czt:ui-pickclip ( / tx)
  (setq tx (czt:clip))
  (cond
    ((null tx)
     (czt:ui-log "[CZT] 剪贴板里没有文本 —— 先在生成器网页里点「写回」，再回来点这个按钮。"))
    ((not (czt:okp tx))
     (czt:ui-log (strcat "[CZT] 剪贴板里的内容不像清单（没找到「表头」或「图签」关键字）。" SEP
                         "      确认已经在箱变/KYN28 生成器网页上点了「写回」（会自动复制到剪贴板），"
                         "再回来点这个按钮。")))
    (T
     ;; 记下「当前清单」（写回剪贴板按钮用）；只记任务，立刻关对话框 ——
     ;; 出图必须等对话框关掉之后再做（见文件头注释）
     (setq *czt:ui-cur* (list "剪贴板" tx))
     (setq *czt:ui-job* (list "text" tx (czt:ui-flags)))
     (done_dialog 1))
  )
  (princ)
)

;; 「改从 TXT 文件读取…」按钮（旧的选文件流程，留作备用入口）
(defun czt:ui-pickfile ()
  ;; 选文件也是模态（getfiled），同样放到对话框关掉之后，避免两种模态打架
  (setq *czt:ui-job* (list "file" nil (czt:ui-flags)))
  (done_dialog 2)
  (princ)
)

;; 刷新状态行：报图上实况（导出按钮取的就是图上数据）
(defun czt:ui-refresh ( / sc)
  (setq sc (plt:scan))
  (set_tile "curinfo"
    (strcat "图上：柜 " (itoa (length (car sc)))
            " 台 · 表头 " (itoa (length (cadr sc)))
            " 枚 · 槽 " (itoa (caddr sc))))
)

;; 「从图纸属性块导出清单 -> 剪贴板」按钮
;;   扫当前图纸的属性块（柜块 / 表头块）与图签 TEXT，按 CZT 清单格式原样
;;   拼回来写进剪贴板 —— 全程只读（ssget/entget），不动图、不碰命令行，
;;   所以能直接放在对话框回调里跑（与出图那种必须挪出对话框的动作不同）。
(defun czt:ui-saveclip ( / )
  (czt:ui-log (czt:dumpclip))
  (czt:ui-refresh)
  (princ)
)

;; 对话框关闭后执行真正的动作 —— 这里才是能安全跑 command 的地方
(defun czt:ui-exec ( / job kind tx f r)
  (setq job *czt:ui-job*)
  (setq *czt:ui-job* nil)
  (if job
    (progn
      (setq kind (car job))
      (if (= kind "text")
        (czt:text (nth 1 job) (nth 2 job))
        (progn
          (setq f (getfiled "选清单文件（ANSI/GBK 或 UTF-8 的 txt）" "" "txt" 0))
          (if (or (null f) (= f ""))
            (princ "\n[CZT] 取消了，没选文件。")
            (progn
              ;; 顺手留一份原文当「当前清单」（编码自适应与 czt:go 同口径）
              (setq tx (czt:readfile f))
              (if (czt:okp tx) (setq *czt:ui-cur* (list (vl-filename-base f) tx)))
              (czt:go f (nth 2 job))
            )
          )
        )
      )
    )
  )
  (princ)
)

;; 运行时把对话框描述写成一个临时 .dcl 文件（用完即删）
(defun czt:ui-dcl ( / f h)
  (setq f (vl-filename-mktemp "czt" nil ".dcl"))
  (setq h (open f "w"))
  (if h
    (progn
      (write-line "czt_dlg : dialog {" h)
      (write-line "  label = \"属性块 - 一键出图（CZT）\";" h)
      (write-line "  : boxed_column {" h)
      (write-line "    label = \"第 1 步 · 准备清单\";" h)
      (write-line "    : text { label = \"在「箱变生成器」或「KYN28 生成器」网页上点一下「写回」按钮，\"; }" h)
      (write-line "    : text { label = \"它会自动把清单文本复制到剪贴板（本机也认手工整理的同格式文本）。\"; }" h)
      (write-line "  }" h)
      (write-line "  : boxed_row {" h)
      (write-line "    label = \"第 2 步 · 出图方式\";" h)
      (write-line "    : radio_column {" h)
      (write-line "      label = \"判型\";" h)
      (write-line "      : radio_button { key = \"m_auto\";  label = \"自动判型（推荐）\"; }" h)
      (write-line "      : radio_button { key = \"m_kyn28\"; label = \"强制 KYN28\"; }" h)
      (write-line "      : radio_button { key = \"m_xbw\";   label = \"强制箱变两段\"; }" h)
      (write-line "    }" h)
      (write-line "    : column {" h)
      (write-line "      : toggle { key = \"dry\";  label = \"只预演，不写图\"; }" h)
      (write-line "      : toggle { key = \"wipe\"; label = \"先清空当前空间再重铺（危险）\"; }" h)
      (write-line "    }" h)
      (write-line "  }" h)
      (write-line "  : boxed_row {" h)
      (write-line "    label = \"第 3 步 · 一键执行\";" h)
      (write-line "    : button { key = \"runclip\"; label = \"粘贴剪贴板清单 → 一键出图\"; is_default = true; width = 32; fixed_width = true; }" h)
      (write-line "    : button { key = \"runfile\"; label = \"改从 TXT 文件读取…\"; width = 20; fixed_width = true; }" h)
      (write-line "  }" h)
      (write-line "  : boxed_row {" h)
      (write-line "    label = \"数据回流（图上数据 → 剪贴板）\";" h)
      (write-line "    : button { key = \"saveclip\"; label = \"从图纸属性块导出清单 → 剪贴板\"; width = 34; fixed_width = true; }" h)
      (write-line "    : text { key = \"curinfo\"; label = \"图上：—\"; width = 28; }" h)
      (write-line "  }" h)
      (write-line "  : boxed_column {" h)
      (write-line "    label = \"回包 / 日志\";" h)
      (write-line "    : list_box { key = \"log\"; height = 14; width = 62; }" h)
      (write-line "  }" h)
      (write-line "  spacer;" h)
      (write-line "  : button { key = \"closebtn\"; label = \"关闭\"; is_cancel = true; width = 12; fixed_width = true; }" h)
      (write-line "}" h)
      (close h)
      f
    )
    nil
  )
)

;; 打开交互入口：一次性粘贴（剪贴板）或选文件，点按钮直接出图
(defun czt:ui ( / dclf dcl_id)
  (setq dclf (czt:ui-dcl))
  (cond
    ((null dclf)
     (princ (strcat SEP "[CZT] 临时 DCL 文件写不出来，改用命令行流程：(czt:go \"路径\")。")))
    (T
     (setq dcl_id (load_dialog dclf))
     (cond
       ((< dcl_id 0)
        (princ (strcat SEP "[CZT] DCL 加载失败，改用命令行流程：(czt:go \"路径\")。")))
       ((not (new_dialog "czt_dlg" dcl_id))
        (princ (strcat SEP "[CZT] 对话框初始化失败。"))
        (unload_dialog dcl_id))
       (T
        (set_tile "m_auto" "1")
        (action_tile "runclip"  "(czt:ui-pickclip)")
        (action_tile "runfile"  "(czt:ui-pickfile)")
        (action_tile "saveclip" "(czt:ui-saveclip)")
        (action_tile "closebtn" "(done_dialog)")
        (czt:ui-refresh)
        (setq *czt:ui-job* nil)
        (setq *czt:dcl* T)
        (start_dialog)
        (setq *czt:dcl* nil)
        (unload_dialog dcl_id)
        (czt:ui-exec))
     )
     (if (findfile dclf) (vl-catch-all-apply 'vl-file-delete (list dclf)))
    )
  )
  (princ)
)

;; ================================================================
;; 八、入口命令
;; ================================================================

;; CZT：打开交互入口 —— 粘贴剪贴板清单，或改选 txt 文件，点按钮一键出图
(defun c:CZT ( / )
  (czt:ensure)
  (czt:ui)
  (princ)
)

(princ (strcat SEP "属性块-一键出图.lsp 已加载（集成单文件版）。"
               SEP "  命令 CZT          打开交互入口：粘贴剪贴板清单 / 选 txt 文件，一键出图"
               SEP "  (czt:auto \"路径\")   (czt:go \"路径\" \"kyn28\"/\"xbw\"/\"dry\"/\"wipe\"/nil)   (czt:dry \"路径\")   (czt:text \"清单文本\" nil)"
               SEP "  转发：czt:slot 改槽 / czt:row 行高 / czt:title 图签 / czt:add 元件 / czt:width 柜宽 / czt:swap 换槽"
               SEP "  回流：界面「从图纸属性块导出清单 → 剪贴板」按钮 / (czt:dump) 取文本 / (czt:dumpclip) 导出并写剪贴板"))
(princ)
